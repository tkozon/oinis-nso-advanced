module oinis-nc-ned-nc-1.0 {
  yang-version 1.1;
  namespace "http://tail-f.com/ns/ned-id/oinis-nc-ned-nc-1.0";
  prefix oinis-nc-ned-nc-1.0;

  import oinis-nc-ned-nc {
    prefix family;
  }

  identity oinis-nc-ned-nc-1.0 {
    base family:oinis-nc-ned-nc;
  }
}
