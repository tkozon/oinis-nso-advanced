module openconfig-platform-linecard {
  // Generated by yanger -t ncs
  tailf:mount-id "oinis-nc-ned-nc-1.0:oinis-nc-ned-nc-1.0";
  tailf:ncs-device-type "netconf";

  yang-version 1;
  namespace "http://openconfig.net/yang/platform/linecard";
  prefix oc-linecard;

  import openconfig-platform {
    prefix oc-platform;
  }
  import openconfig-extensions {
    prefix oc-ext;
  }
  import tailf-common {
    prefix tailf;
  }
  import tailf-ncs {
    prefix ncs;
  }

  organization
    "OpenConfig working group";
  contact
    "OpenConfig working group
     www.openconfig.net";
  description
    "This module defines data related to LINECARD components in
     the openconfig-platform model";
  oc-ext:openconfig-version "1.0.0";

  revision 2022-07-28 {
    description
      "Remove leaf power-admin-state and use a common definition
       instead.";
    reference "1.0.0";
  }
  revision 2022-04-21 {
    description
      "Add platform utilization to linecard.";
    reference "0.2.0";
  }
  revision 2020-05-10 {
    description
      "Remove when statement that references read-only entity from
       a read-write context.";
    reference "0.1.2";
  }
  revision 2018-11-21 {
    description
      "Add OpenConfig module metadata extensions.";
    reference "0.1.1";
  }
  revision 2017-08-03 {
    description
      "Initial revision";
    reference "0.1.0";
  }
  oc-ext:regexp-posix;
  oc-ext:catalog-organization "openconfig";
  oc-ext:origin "openconfig";

  grouping ncs_compliance_template_linecard-config {
    description
      "Configuration data for linecard components";
    uses oc-platform:ncs_compliance_template_component-power-management;
  }

  grouping ncs_compliance_template_linecard-state {
    description
      "Operational state data for linecard components";
    leaf slot-id {
      type string;
      description
        "Identifier for the slot or chassis position in which the
         linecard is installed";
    }
  }

  grouping ncs_compliance_template_linecard-top {
    description
      "Top-level grouping for linecard data";
    container linecard {
      description
        "Top-level container for linecard data";
      container config {
        description
          "Configuration data for linecards";
        uses ncs_compliance_template_linecard-config;
      }
      // NCS drop config false container state
      uses oc-platform:ncs_compliance_template_platform-utilization-top;
    }
  }

  grouping ncs_template_linecard-config {
    description
      "Configuration data for linecard components";
    uses oc-platform:ncs_template_component-power-management;
  }

  grouping ncs_template_linecard-state {
    description
      "Operational state data for linecard components";
    leaf slot-id {
      type string;
      description
        "Identifier for the slot or chassis position in which the
         linecard is installed";
    }
  }

  grouping ncs_template_linecard-top {
    description
      "Top-level grouping for linecard data";
    container linecard {
      description
        "Top-level container for linecard data";
      container config {
        description
          "Configuration data for linecards";
        uses ncs_template_linecard-config;
      }
      // NCS drop config false container state
      uses oc-platform:ncs_template_platform-utilization-top;
    }
  }

  grouping ncs_rpc_notif_linecard-config {
    description
      "Configuration data for linecard components";
    uses oc-platform:ncs_rpc_notif_component-power-management;
  }

  grouping ncs_rpc_notif_linecard-state {
    description
      "Operational state data for linecard components";
    leaf slot-id {
      type string;
      description
        "Identifier for the slot or chassis position in which the
         linecard is installed";
    }
  }

  grouping ncs_rpc_notif_linecard-top {
    description
      "Top-level grouping for linecard data";
    container linecard {
      description
        "Top-level container for linecard data";
      container config {
        description
          "Configuration data for linecards";
        uses ncs_rpc_notif_linecard-config;
      }
      container state {
        config false;
        description
          "Operational state data for linecards";
        uses ncs_rpc_notif_linecard-config;
        uses ncs_rpc_notif_linecard-state;
      }
      uses oc-platform:ncs_rpc_notif_platform-utilization-top;
    }
  }

  grouping live_ncs_linecard-config {
    description
      "Configuration data for linecard components";
    uses oc-platform:live_ncs_component-power-management;
  }

  grouping live_ncs_linecard-state {
    description
      "Operational state data for linecard components";
    leaf slot-id {
      type string;
      description
        "Identifier for the slot or chassis position in which the
         linecard is installed";
    }
  }

  grouping live_ncs_linecard-top {
    description
      "Top-level grouping for linecard data";
    container linecard {
      description
        "Top-level container for linecard data";
      container config {
        description
          "Configuration data for linecards";
        uses live_ncs_linecard-config;
      }
      container state {
        description
          "Operational state data for linecards";
        uses live_ncs_linecard-config;
        uses live_ncs_linecard-state;
      }
      uses oc-platform:live_ncs_platform-utilization-top;
    }
  }

  grouping linecard-config {
    description
      "Configuration data for linecard components";
    uses oc-platform:component-power-management;
  }

  grouping linecard-state {
    description
      "Operational state data for linecard components";
    leaf slot-id {
      type string;
      description
        "Identifier for the slot or chassis position in which the
         linecard is installed";
    }
  }

  grouping linecard-top {
    description
      "Top-level grouping for linecard data";
    container linecard {
      description
        "Top-level container for linecard data";
      container config {
        description
          "Configuration data for linecards";
        uses linecard-config;
      }
      // NCS drop config false container state
      uses oc-platform:platform-utilization-top;
    }
  }

  augment "/ncs:compliance/ncs:template/ncs:ned-id/ncs:config/oc-platform:components/oc-platform:component" {
    description
      "Adding linecard data to physical inventory. This subtree
       is only valid when the type of the component is LINECARD.";
    uses ncs_compliance_template_linecard-top;
  }
  augment "/ncs:devices/ncs:template/ncs:ned-id/ncs:config/oc-platform:components/oc-platform:component" {
    description
      "Adding linecard data to physical inventory. This subtree
       is only valid when the type of the component is LINECARD.";
    uses ncs_template_linecard-top;
  }
  augment "/ncs:devices/ncs:device/ncs:live-status/oc-platform:components/oc-platform:component" {
    description
      "Adding linecard data to physical inventory. This subtree
       is only valid when the type of the component is LINECARD.";
    uses live_ncs_linecard-top {
      refine linecard {
        tailf:ncs-device-type "netconf";
        tailf:display-when "not(../../../../ncs:module) or ../../../../ncs:module[ncs:name='openconfig-platform-linecard'] or (../../../../ncs:live-status-protocol[not(ncs:capability)]) or (../../../../ncs:live-status-protocol/ncs:capability/ncs:module[.='openconfig-platform-linecard'])";
      }
    }
  }
  augment "/ncs:devices/ncs:device/ncs:config/oc-platform:components/oc-platform:component" {
    description
      "Adding linecard data to physical inventory. This subtree
       is only valid when the type of the component is LINECARD.";
    uses linecard-top {
      refine linecard {
        tailf:ncs-device-type "netconf";
        tailf:display-when "not(../../../../ncs:module) or ../../../../ncs:module[ncs:name='openconfig-platform-linecard']";
      }
    }
  }
}
