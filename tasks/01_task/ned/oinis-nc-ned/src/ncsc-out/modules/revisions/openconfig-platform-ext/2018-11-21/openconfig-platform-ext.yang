module openconfig-platform-ext {
  // Generated by yanger -t ncs
  tailf:mount-id "oinis-nc-ned-nc-1.0:oinis-nc-ned-nc-1.0";
  tailf:ncs-device-type "netconf";

  yang-version 1;
  namespace "http://openconfig.net/yang/platform/extension";
  prefix oc-platform-ext;

  import openconfig-platform {
    prefix oc-platform;
  }
  import openconfig-extensions {
    prefix oc-ext;
  }
  import tailf-common {
    prefix tailf;
  }
  import tailf-ncs {
    prefix ncs;
  }

  organization
    "OpenConfig working group";
  contact
    "OpenConfig working group
     www.openconfig.net";
  description
    "This module defines optional extensions to the OpenConfig
     platform model.";
  oc-ext:openconfig-version "0.1.1";

  revision 2018-11-21 {
    description
      "Add OpenConfig module metadata extensions.";
    reference "0.1.1";
  }
  revision 2018-01-18 {
    description
      "Initial revision";
    reference "0.1.0";
  }
  oc-ext:regexp-posix;
  oc-ext:catalog-organization "openconfig";
  oc-ext:origin "openconfig";

  grouping ncs_compliance_template_platform-component-ext-state {
    description
      "Operational state data for platform components";
    leaf entity-id {
      type string;
      description
        "A unique numeric identifier assigned by the system to the
         component. This identifier may be used to represent the
         corresponding SNMP Entity MIB identifier.";
    }
  }

  grouping ncs_template_platform-component-ext-state {
    description
      "Operational state data for platform components";
    leaf entity-id {
      type string;
      description
        "A unique numeric identifier assigned by the system to the
         component. This identifier may be used to represent the
         corresponding SNMP Entity MIB identifier.";
    }
  }

  grouping ncs_rpc_notif_platform-component-ext-state {
    description
      "Operational state data for platform components";
    leaf entity-id {
      type uint32;
      description
        "A unique numeric identifier assigned by the system to the
         component. This identifier may be used to represent the
         corresponding SNMP Entity MIB identifier.";
    }
  }

  grouping live_ncs_platform-component-ext-state {
    description
      "Operational state data for platform components";
    leaf entity-id {
      type uint32;
      description
        "A unique numeric identifier assigned by the system to the
         component. This identifier may be used to represent the
         corresponding SNMP Entity MIB identifier.";
    }
  }

  grouping platform-component-ext-state {
    description
      "Operational state data for platform components";
    leaf entity-id {
      type uint32;
      description
        "A unique numeric identifier assigned by the system to the
         component. This identifier may be used to represent the
         corresponding SNMP Entity MIB identifier.";
    }
  }

  augment "/ncs:devices/ncs:device/ncs:live-status/oc-platform:components/oc-platform:component/oc-platform:state" {
    description
      "Adding extension state data to components";
    uses live_ncs_platform-component-ext-state {
      refine entity-id {
        tailf:ncs-device-type "netconf";
        tailf:display-when "not(../../../../../ncs:module) or ../../../../../ncs:module[ncs:name='openconfig-platform-ext'] or (../../../../../ncs:live-status-protocol[not(ncs:capability)]) or (../../../../../ncs:live-status-protocol/ncs:capability/ncs:module[.='openconfig-platform-ext'])";
      }
    }
  }
}
