module openconfig-if-poe {
  // Generated by yanger -t ncs
  tailf:mount-id "oinis-nc-ned-nc-1.0:oinis-nc-ned-nc-1.0";
  tailf:ncs-device-type "netconf";

  yang-version 1;
  namespace "http://openconfig.net/yang/poe";
  prefix oc-poe;

  import openconfig-if-ethernet {
    prefix oc-eth;
  }
  import openconfig-interfaces {
    prefix oc-if;
  }
  import openconfig-extensions {
    prefix oc-ext;
  }
  import tailf-common {
    prefix tailf;
  }
  import tailf-ncs {
    prefix ncs;
  }

  organization
    "OpenConfig working group";
  contact
    "Openconfig working group
     www.openconfig.net";
  description
    "This module defines configuration and state data for
     Power over Ethernet (PoE) based on the IEEE 802.3af
     standard.";
  oc-ext:openconfig-version "0.1.1";

  revision 2018-11-21 {
    description
      "Add OpenConfig module metadata extensions.";
    reference "0.1.1";
  }
  revision 2017-09-14 {
    description
      "Initial public revision";
    reference "0.1.0";
  }
  oc-ext:regexp-posix;
  oc-ext:catalog-organization "openconfig";
  oc-ext:origin "openconfig";

  grouping ncs_compliance_template_poe-ethernet-config {
    description
      "PoE ethernet config grouping";
    leaf enabled {
      type string;
      // NCS drop default statement
      description
        "Enable or disable PoE in the ethernet interface.";
    }
  }

  grouping ncs_compliance_template_poe-ethernet-state {
    description
      "PoE ethernet state grouping";
    leaf power-used {
      type string;
      units "Watts";
      description
        "Power used by the ethernet interface in Watts.";
    }
    leaf power-class {
      type string;
      description
        "IEEE 802.3af Power class detected for this ethernet
         interface.";
    }
  }

  grouping ncs_compliance_template_poe-ethernet-top {
    description
      "Ethernet top level grouping";
    container poe {
      description
        "Top-level container for PoE configuration and state data";
      container config {
        description
          "Configuration data for PoE";
        uses ncs_compliance_template_poe-ethernet-config;
      }
      // NCS drop config false container state
    }
  }

  grouping ncs_template_poe-ethernet-config {
    description
      "PoE ethernet config grouping";
    leaf enabled {
      type string;
      // NCS drop default statement
      description
        "Enable or disable PoE in the ethernet interface.";
    }
  }

  grouping ncs_template_poe-ethernet-state {
    description
      "PoE ethernet state grouping";
    leaf power-used {
      type string;
      units "Watts";
      description
        "Power used by the ethernet interface in Watts.";
    }
    leaf power-class {
      type string;
      description
        "IEEE 802.3af Power class detected for this ethernet
         interface.";
    }
  }

  grouping ncs_template_poe-ethernet-top {
    description
      "Ethernet top level grouping";
    container poe {
      description
        "Top-level container for PoE configuration and state data";
      container config {
        description
          "Configuration data for PoE";
        uses ncs_template_poe-ethernet-config;
      }
      // NCS drop config false container state
    }
  }

  grouping ncs_rpc_notif_poe-ethernet-config {
    description
      "PoE ethernet config grouping";
    leaf enabled {
      type boolean;
      default "true";
      description
        "Enable or disable PoE in the ethernet interface.";
    }
  }

  grouping ncs_rpc_notif_poe-ethernet-state {
    description
      "PoE ethernet state grouping";
    leaf power-used {
      type decimal64 {
        fraction-digits 2;
      }
      units "Watts";
      description
        "Power used by the ethernet interface in Watts.";
    }
    leaf power-class {
      type uint8;
      description
        "IEEE 802.3af Power class detected for this ethernet
         interface.";
    }
  }

  grouping ncs_rpc_notif_poe-ethernet-top {
    description
      "Ethernet top level grouping";
    container poe {
      description
        "Top-level container for PoE configuration and state data";
      container config {
        description
          "Configuration data for PoE";
        uses ncs_rpc_notif_poe-ethernet-config;
      }
      container state {
        config false;
        description
          "Operational state data for PoE";
        uses ncs_rpc_notif_poe-ethernet-config;
        uses ncs_rpc_notif_poe-ethernet-state;
      }
    }
  }

  grouping live_ncs_poe-ethernet-config {
    description
      "PoE ethernet config grouping";
    leaf enabled {
      type boolean;
      // NCS drop default statement
      description
        "Enable or disable PoE in the ethernet interface.";
    }
  }

  grouping live_ncs_poe-ethernet-state {
    description
      "PoE ethernet state grouping";
    leaf power-used {
      type decimal64 {
        fraction-digits 2;
      }
      units "Watts";
      description
        "Power used by the ethernet interface in Watts.";
    }
    leaf power-class {
      type uint8;
      description
        "IEEE 802.3af Power class detected for this ethernet
         interface.";
    }
  }

  grouping live_ncs_poe-ethernet-top {
    description
      "Ethernet top level grouping";
    container poe {
      description
        "Top-level container for PoE configuration and state data";
      container config {
        description
          "Configuration data for PoE";
        uses live_ncs_poe-ethernet-config;
      }
      container state {
        description
          "Operational state data for PoE";
        uses live_ncs_poe-ethernet-config;
        uses live_ncs_poe-ethernet-state;
      }
    }
  }

  grouping poe-ethernet-config {
    description
      "PoE ethernet config grouping";
    leaf enabled {
      type boolean;
      default "true";
      description
        "Enable or disable PoE in the ethernet interface.";
    }
  }

  grouping poe-ethernet-state {
    description
      "PoE ethernet state grouping";
    leaf power-used {
      type decimal64 {
        fraction-digits 2;
      }
      units "Watts";
      description
        "Power used by the ethernet interface in Watts.";
    }
    leaf power-class {
      type uint8;
      description
        "IEEE 802.3af Power class detected for this ethernet
         interface.";
    }
  }

  grouping poe-ethernet-top {
    description
      "Ethernet top level grouping";
    container poe {
      description
        "Top-level container for PoE configuration and state data";
      container config {
        description
          "Configuration data for PoE";
        uses poe-ethernet-config;
      }
      // NCS drop config false container state
    }
  }

  augment "/ncs:compliance/ncs:template/ncs:ned-id/ncs:config/oc-if:interfaces/oc-if:interface/oc-eth:ethernet" {
    description
      "Adds PoE to the ethernet model.";
    uses ncs_compliance_template_poe-ethernet-top;
  }
  augment "/ncs:devices/ncs:template/ncs:ned-id/ncs:config/oc-if:interfaces/oc-if:interface/oc-eth:ethernet" {
    description
      "Adds PoE to the ethernet model.";
    uses ncs_template_poe-ethernet-top;
  }
  augment "/ncs:devices/ncs:device/ncs:live-status/oc-if:interfaces/oc-if:interface/oc-eth:ethernet" {
    description
      "Adds PoE to the ethernet model.";
    uses live_ncs_poe-ethernet-top {
      refine poe {
        tailf:ncs-device-type "netconf";
        tailf:display-when "not(../../../../../ncs:module) or ../../../../../ncs:module[ncs:name='openconfig-if-poe'] or (../../../../../ncs:live-status-protocol[not(ncs:capability)]) or (../../../../../ncs:live-status-protocol/ncs:capability/ncs:module[.='openconfig-if-poe'])";
      }
    }
  }
  augment "/ncs:devices/ncs:device/ncs:config/oc-if:interfaces/oc-if:interface/oc-eth:ethernet" {
    description
      "Adds PoE to the ethernet model.";
    uses poe-ethernet-top {
      refine poe {
        tailf:ncs-device-type "netconf";
        tailf:display-when "not(../../../../../ncs:module) or ../../../../../ncs:module[ncs:name='openconfig-if-poe']";
      }
    }
  }
}
