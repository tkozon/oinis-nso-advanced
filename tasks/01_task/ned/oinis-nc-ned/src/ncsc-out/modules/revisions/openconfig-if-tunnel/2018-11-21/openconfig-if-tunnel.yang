module openconfig-if-tunnel {
  // Generated by yanger -t ncs
  tailf:mount-id "oinis-nc-ned-nc-1.0:oinis-nc-ned-nc-1.0";
  tailf:ncs-device-type "netconf";

  yang-version 1;
  namespace "http://openconfig.net/yang/interfaces/tunnel";
  prefix oc-tun;

  import openconfig-interfaces {
    prefix oc-if;
  }
  import openconfig-extensions {
    prefix oc-ext;
  }
  import openconfig-inet-types {
    prefix oc-inet;
  }
  import openconfig-if-ip {
    prefix oc-ip;
  }
  import tailf-common {
    prefix tailf;
  }
  import tailf-ncs {
    prefix ncs;
  }

  organization
    "OpenConfig working group";
  contact
    "OpenConfig working group
     netopenconfig@googlegroups.com";
  description
    "This model adds extensions to the OpenConfig interfaces
     model to configure tunnel interfaces on a network
     device.";
  oc-ext:openconfig-version "0.1.1";

  revision 2018-11-21 {
    description
      "Add OpenConfig module metadata extensions.";
    reference "0.1.1";
  }
  revision 2018-01-05 {
    description
      "Initial tunnel model";
    reference "0.1.0";
  }
  oc-ext:regexp-posix;
  oc-ext:catalog-organization "openconfig";
  oc-ext:origin "openconfig";

  grouping ncs_compliance_template_tunnel-top {
    description
      "Top-level grouping for parameters related to
       a tunnel interface.";
    container tunnel {
      description
        "In the case that the interface is logical tunnel
         interface, the parameters for the tunnel are
         specified within this subtree. Tunnel interfaces
         have only a single logical subinterface associated
         with them.";
      container config {
        description
          "Configuration parameters associated with the
           tunnel interface";
        uses ncs_compliance_template_tunnel-config;
      }
      // NCS drop config false container state
      uses oc-ip:ncs_compliance_template_ipv4-top;
      uses oc-ip:ncs_compliance_template_ipv6-top;
    }
  }

  grouping ncs_compliance_template_tunnel-config {
    description
      "Configuraton parameters relating to a tunnel
       interface.";
    leaf src {
      type oc-inet:ncs_compliance_template_ip-address;
      description
        "The source address that should be used for the
         tunnel.";
    }
    leaf dst {
      type oc-inet:ncs_compliance_template_ip-address;
      description
        "The destination address for the tunnel.";
    }
    leaf ttl {
      type string;
      description
        "The time-to-live (or hop limit) that should be utilised
         for the IP packets used for the tunnel transport.";
    }
    leaf gre-key {
      type string;
      description
        "The GRE key to be specified for the tunnel. The
         key is used to identify a traffic flow within
         a tunnel.";
      reference "RFC2890: Key and Sequence Number Extensions to GRE";
    }
  }

  grouping ncs_template_tunnel-top {
    description
      "Top-level grouping for parameters related to
       a tunnel interface.";
    container tunnel {
      description
        "In the case that the interface is logical tunnel
         interface, the parameters for the tunnel are
         specified within this subtree. Tunnel interfaces
         have only a single logical subinterface associated
         with them.";
      container config {
        description
          "Configuration parameters associated with the
           tunnel interface";
        uses ncs_template_tunnel-config;
      }
      // NCS drop config false container state
      uses oc-ip:ncs_template_ipv4-top;
      uses oc-ip:ncs_template_ipv6-top;
    }
  }

  grouping ncs_template_tunnel-config {
    description
      "Configuraton parameters relating to a tunnel
       interface.";
    leaf src {
      type oc-inet:ncs_template_ip-address;
      description
        "The source address that should be used for the
         tunnel.";
    }
    leaf dst {
      type oc-inet:ncs_template_ip-address;
      description
        "The destination address for the tunnel.";
    }
    leaf ttl {
      type string;
      description
        "The time-to-live (or hop limit) that should be utilised
         for the IP packets used for the tunnel transport.";
    }
    leaf gre-key {
      type string;
      description
        "The GRE key to be specified for the tunnel. The
         key is used to identify a traffic flow within
         a tunnel.";
      reference "RFC2890: Key and Sequence Number Extensions to GRE";
    }
  }

  grouping ncs_rpc_notif_tunnel-top {
    description
      "Top-level grouping for parameters related to
       a tunnel interface.";
    container tunnel {
      description
        "In the case that the interface is logical tunnel
         interface, the parameters for the tunnel are
         specified within this subtree. Tunnel interfaces
         have only a single logical subinterface associated
         with them.";
      container config {
        description
          "Configuration parameters associated with the
           tunnel interface";
        uses ncs_rpc_notif_tunnel-config;
      }
      container state {
        config false;
        description
          "Operational state parameters associated with
           the tunnel interface.";
        uses ncs_rpc_notif_tunnel-config;
      }
      uses oc-ip:ncs_rpc_notif_ipv4-top;
      uses oc-ip:ncs_rpc_notif_ipv6-top;
    }
  }

  grouping ncs_rpc_notif_tunnel-config {
    description
      "Configuraton parameters relating to a tunnel
       interface.";
    leaf src {
      type oc-inet:ncs_rpc_notif_ip-address;
      description
        "The source address that should be used for the
         tunnel.";
    }
    leaf dst {
      type oc-inet:ncs_rpc_notif_ip-address;
      description
        "The destination address for the tunnel.";
    }
    leaf ttl {
      type uint8 {
        range "1..255";
      }
      description
        "The time-to-live (or hop limit) that should be utilised
         for the IP packets used for the tunnel transport.";
    }
    leaf gre-key {
      type uint32;
      description
        "The GRE key to be specified for the tunnel. The
         key is used to identify a traffic flow within
         a tunnel.";
      reference "RFC2890: Key and Sequence Number Extensions to GRE";
    }
  }

  grouping live_ncs_tunnel-top {
    description
      "Top-level grouping for parameters related to
       a tunnel interface.";
    container tunnel {
      description
        "In the case that the interface is logical tunnel
         interface, the parameters for the tunnel are
         specified within this subtree. Tunnel interfaces
         have only a single logical subinterface associated
         with them.";
      container config {
        description
          "Configuration parameters associated with the
           tunnel interface";
        uses live_ncs_tunnel-config;
      }
      container state {
        description
          "Operational state parameters associated with
           the tunnel interface.";
        uses live_ncs_tunnel-config;
      }
      uses oc-ip:live_ncs_ipv4-top;
      uses oc-ip:live_ncs_ipv6-top;
    }
  }

  grouping live_ncs_tunnel-config {
    description
      "Configuraton parameters relating to a tunnel
       interface.";
    leaf src {
      type oc-inet:live_ncs_ip-address;
      description
        "The source address that should be used for the
         tunnel.";
    }
    leaf dst {
      type oc-inet:live_ncs_ip-address;
      description
        "The destination address for the tunnel.";
    }
    leaf ttl {
      type uint8 {
        range "1..255";
      }
      description
        "The time-to-live (or hop limit) that should be utilised
         for the IP packets used for the tunnel transport.";
    }
    leaf gre-key {
      type uint32;
      description
        "The GRE key to be specified for the tunnel. The
         key is used to identify a traffic flow within
         a tunnel.";
      reference "RFC2890: Key and Sequence Number Extensions to GRE";
    }
  }

  grouping tunnel-top {
    description
      "Top-level grouping for parameters related to
       a tunnel interface.";
    container tunnel {
      description
        "In the case that the interface is logical tunnel
         interface, the parameters for the tunnel are
         specified within this subtree. Tunnel interfaces
         have only a single logical subinterface associated
         with them.";
      container config {
        description
          "Configuration parameters associated with the
           tunnel interface";
        uses tunnel-config;
      }
      // NCS drop config false container state
      uses oc-ip:ipv4-top;
      uses oc-ip:ipv6-top;
    }
  }

  grouping tunnel-config {
    description
      "Configuraton parameters relating to a tunnel
       interface.";
    leaf src {
      type oc-inet:ip-address;
      description
        "The source address that should be used for the
         tunnel.";
    }
    leaf dst {
      type oc-inet:ip-address;
      description
        "The destination address for the tunnel.";
    }
    leaf ttl {
      type uint8 {
        range "1..255";
      }
      description
        "The time-to-live (or hop limit) that should be utilised
         for the IP packets used for the tunnel transport.";
    }
    leaf gre-key {
      type uint32;
      description
        "The GRE key to be specified for the tunnel. The
         key is used to identify a traffic flow within
         a tunnel.";
      reference "RFC2890: Key and Sequence Number Extensions to GRE";
    }
  }

  augment "/ncs:compliance/ncs:template/ncs:ned-id/ncs:config/oc-if:interfaces/oc-if:interface" {
    description
      "Augment to add tunnel configuration to interfaces";
    uses ncs_compliance_template_tunnel-top;
  }
  augment "/ncs:devices/ncs:template/ncs:ned-id/ncs:config/oc-if:interfaces/oc-if:interface" {
    description
      "Augment to add tunnel configuration to interfaces";
    uses ncs_template_tunnel-top;
  }
  augment "/ncs:devices/ncs:device/ncs:live-status/oc-if:interfaces/oc-if:interface" {
    description
      "Augment to add tunnel configuration to interfaces";
    uses live_ncs_tunnel-top {
      refine tunnel {
        tailf:ncs-device-type "netconf";
        tailf:display-when "not(../../../../ncs:module) or ../../../../ncs:module[ncs:name='openconfig-if-tunnel'] or (../../../../ncs:live-status-protocol[not(ncs:capability)]) or (../../../../ncs:live-status-protocol/ncs:capability/ncs:module[.='openconfig-if-tunnel'])";
      }
    }
  }
  augment "/ncs:devices/ncs:device/ncs:config/oc-if:interfaces/oc-if:interface" {
    description
      "Augment to add tunnel configuration to interfaces";
    uses tunnel-top {
      refine tunnel {
        tailf:ncs-device-type "netconf";
        tailf:display-when "not(../../../../ncs:module) or ../../../../ncs:module[ncs:name='openconfig-if-tunnel']";
      }
    }
  }
}
