submodule openconfig-platform-common {
  // Generated by yanger -t ncs
  tailf:mount-id "oinis-nc-ned-nc-1.0:oinis-nc-ned-nc-1.0";

  yang-version 1;
  belongs-to openconfig-platform {
    prefix oc-platform;
  }

  import openconfig-platform-types {
    prefix oc-platform-types;
  }
  import openconfig-extensions {
    prefix oc-ext;
  }
  import openconfig-types {
    prefix oc-types;
  }
  import tailf-common {
    prefix tailf;
  }
  import tailf-ncs {
    prefix ncs;
  }

  organization
    "OpenConfig working group";
  contact
    "OpenConfig working group
     www.openconfig.net";
  description
    "This modules contains common groupings that are used in multiple
     components within the platform module.";
  oc-ext:openconfig-version "0.20.0";

  revision 2022-08-31 {
    description
      "Add new state data for component CLEI code.";
    reference "0.20.0";
  }
  revision 2022-07-28 {
    description
      "Add grouping for component power management";
    reference "0.19.0";
  }
  revision 2022-07-11 {
    description
      "Add switchover ready";
    reference "0.18.0";
  }
  revision 2022-06-10 {
    description
      "Specify units and epoch for switchover and reboot times.";
    reference "0.17.0";
  }
  revision 2022-04-21 {
    description
      "Add platform utilization.";
    reference "0.16.0";
  }

  grouping ncs_compliance_template_platform-utilization-top {
    description
      "Top level of utilization.";
    container utilization {
      description
        "Utilization of the component.";
      container resources {
        description
          "Enclosing container for the resources in this component.";
        list resource {
          // NCS patched for predictable order
          ordered-by user;
          key "name";
          description
            "List of resources, keyed by resource name.";
          leaf name {
            type string;
            description
              "References the resource name.";
          }
          container config {
            description
              "Configuration data for each resource.";
            uses ncs_compliance_template_platform-utilization-resource-config;
          }
          // NCS drop config false container state
        }
      }
    }
  }

  grouping ncs_compliance_template_platform-utilization-resource-config {
    description
      "Configuration data for utilization resource.";
    leaf name {
      type string;
      description
        "Resource name within the component.";
    }
  }

  grouping ncs_compliance_template_platform-utilization-resource-state {
    description
      "Operational state data for utilization resource.";
    leaf used {
      type string;
      description
        "Number of entries currently in use for the resource.";
    }
    leaf committed {
      type string;
      description
        "Number of entries currently reserved for this resource. This is only
         relevant to tables which allocate a block of resource for a given
         feature.";
    }
    leaf free {
      type string;
      description
        "Number of entries available to use.";
    }
    leaf max-limit {
      type string;
      description
        "Maximum number of entries available for the resource. The value
         is the theoretical maximum resource utilization possible.";
    }
    leaf high-watermark {
      type string;
      description
        "A watermark of highest number of entries used for this resource.";
    }
    leaf last-high-watermark {
      type oc-types:ncs_compliance_template_timeticks64;
      description
        "The time when the high-watermark was last updated";
    }
  }

  grouping ncs_compliance_template_component-power-management {
    description
      "Common grouping for managing component power";
    leaf power-admin-state {
      type oc-platform-types:ncs_compliance_template_component-power-type;
      // NCS drop default statement
      description
        "Enable or disable power to the component";
    }
  }

  grouping ncs_template_platform-utilization-top {
    description
      "Top level of utilization.";
    container utilization {
      description
        "Utilization of the component.";
      container resources {
        description
          "Enclosing container for the resources in this component.";
        list resource {
          // NCS patched for predictable order
          ordered-by user;
          key "name";
          description
            "List of resources, keyed by resource name.";
          leaf name {
            type string;
            description
              "References the resource name.";
          }
          container config {
            description
              "Configuration data for each resource.";
            uses ncs_template_platform-utilization-resource-config;
          }
          // NCS drop config false container state
        }
      }
    }
  }

  grouping ncs_template_platform-utilization-resource-config {
    description
      "Configuration data for utilization resource.";
    leaf name {
      type string;
      description
        "Resource name within the component.";
    }
  }

  grouping ncs_template_platform-utilization-resource-state {
    description
      "Operational state data for utilization resource.";
    leaf used {
      type string;
      description
        "Number of entries currently in use for the resource.";
    }
    leaf committed {
      type string;
      description
        "Number of entries currently reserved for this resource. This is only
         relevant to tables which allocate a block of resource for a given
         feature.";
    }
    leaf free {
      type string;
      description
        "Number of entries available to use.";
    }
    leaf max-limit {
      type string;
      description
        "Maximum number of entries available for the resource. The value
         is the theoretical maximum resource utilization possible.";
    }
    leaf high-watermark {
      type string;
      description
        "A watermark of highest number of entries used for this resource.";
    }
    leaf last-high-watermark {
      type oc-types:ncs_template_timeticks64;
      description
        "The time when the high-watermark was last updated";
    }
  }

  grouping ncs_template_component-power-management {
    description
      "Common grouping for managing component power";
    leaf power-admin-state {
      type oc-platform-types:ncs_template_component-power-type;
      // NCS drop default statement
      description
        "Enable or disable power to the component";
    }
  }

  grouping ncs_rpc_notif_platform-utilization-top {
    description
      "Top level of utilization.";
    container utilization {
      description
        "Utilization of the component.";
      container resources {
        description
          "Enclosing container for the resources in this component.";
        list resource {
          key "name";
          description
            "List of resources, keyed by resource name.";
          leaf name {
            type leafref {
              path "../config/name";
            }
            description
              "References the resource name.";
          }
          container config {
            description
              "Configuration data for each resource.";
            uses ncs_rpc_notif_platform-utilization-resource-config;
          }
          container state {
            config false;
            description
              "Operational state data for each resource.";
            uses ncs_rpc_notif_platform-utilization-resource-config;
            uses ncs_rpc_notif_platform-utilization-resource-state;
          }
        }
      }
    }
  }

  grouping ncs_rpc_notif_platform-utilization-resource-config {
    description
      "Configuration data for utilization resource.";
    leaf name {
      type string;
      description
        "Resource name within the component.";
    }
  }

  grouping ncs_rpc_notif_platform-utilization-resource-state {
    description
      "Operational state data for utilization resource.";
    leaf used {
      type uint64;
      description
        "Number of entries currently in use for the resource.";
    }
    leaf committed {
      type uint64;
      description
        "Number of entries currently reserved for this resource. This is only
         relevant to tables which allocate a block of resource for a given
         feature.";
    }
    leaf free {
      type uint64;
      description
        "Number of entries available to use.";
    }
    leaf max-limit {
      type uint64;
      description
        "Maximum number of entries available for the resource. The value
         is the theoretical maximum resource utilization possible.";
    }
    leaf high-watermark {
      type uint64;
      description
        "A watermark of highest number of entries used for this resource.";
    }
    leaf last-high-watermark {
      type oc-types:ncs_rpc_notif_timeticks64;
      description
        "The time when the high-watermark was last updated";
    }
  }

  grouping ncs_rpc_notif_component-power-management {
    description
      "Common grouping for managing component power";
    leaf power-admin-state {
      type oc-platform-types:ncs_rpc_notif_component-power-type;
      default "POWER_ENABLED";
      description
        "Enable or disable power to the component";
    }
  }

  grouping live_ncs_platform-utilization-top {
    description
      "Top level of utilization.";
    container utilization {
      description
        "Utilization of the component.";
      container resources {
        description
          "Enclosing container for the resources in this component.";
        list resource {
          key "name";
          description
            "List of resources, keyed by resource name.";
          leaf name {
            type leafref {
              path "../config/name";
            }
            description
              "References the resource name.";
          }
          container config {
            description
              "Configuration data for each resource.";
            uses live_ncs_platform-utilization-resource-config;
          }
          container state {
            description
              "Operational state data for each resource.";
            uses live_ncs_platform-utilization-resource-config;
            uses live_ncs_platform-utilization-resource-state;
          }
        }
      }
    }
  }

  grouping live_ncs_platform-utilization-resource-config {
    description
      "Configuration data for utilization resource.";
    leaf name {
      type string;
      description
        "Resource name within the component.";
    }
  }

  grouping live_ncs_platform-utilization-resource-state {
    description
      "Operational state data for utilization resource.";
    leaf used {
      type uint64;
      description
        "Number of entries currently in use for the resource.";
    }
    leaf committed {
      type uint64;
      description
        "Number of entries currently reserved for this resource. This is only
         relevant to tables which allocate a block of resource for a given
         feature.";
    }
    leaf free {
      type uint64;
      description
        "Number of entries available to use.";
    }
    leaf max-limit {
      type uint64;
      description
        "Maximum number of entries available for the resource. The value
         is the theoretical maximum resource utilization possible.";
    }
    leaf high-watermark {
      type uint64;
      description
        "A watermark of highest number of entries used for this resource.";
    }
    leaf last-high-watermark {
      type oc-types:live_ncs_timeticks64;
      description
        "The time when the high-watermark was last updated";
    }
  }

  grouping live_ncs_component-power-management {
    description
      "Common grouping for managing component power";
    leaf power-admin-state {
      type oc-platform-types:live_ncs_component-power-type;
      // NCS drop default statement
      description
        "Enable or disable power to the component";
    }
  }

  grouping platform-utilization-top {
    description
      "Top level of utilization.";
    container utilization {
      description
        "Utilization of the component.";
      container resources {
        description
          "Enclosing container for the resources in this component.";
        list resource {
          key "name";
          description
            "List of resources, keyed by resource name.";
          leaf name {
            type leafref {
              path "../config/name";
            }
            description
              "References the resource name.";
          }
          container config {
            description
              "Configuration data for each resource.";
            uses platform-utilization-resource-config;
          }
          // NCS drop config false container state
        }
      }
    }
  }

  grouping platform-utilization-resource-config {
    description
      "Configuration data for utilization resource.";
    leaf name {
      type string;
      description
        "Resource name within the component.";
    }
  }

  grouping platform-utilization-resource-state {
    description
      "Operational state data for utilization resource.";
    leaf used {
      type uint64;
      description
        "Number of entries currently in use for the resource.";
    }
    leaf committed {
      type uint64;
      description
        "Number of entries currently reserved for this resource. This is only
         relevant to tables which allocate a block of resource for a given
         feature.";
    }
    leaf free {
      type uint64;
      description
        "Number of entries available to use.";
    }
    leaf max-limit {
      type uint64;
      description
        "Maximum number of entries available for the resource. The value
         is the theoretical maximum resource utilization possible.";
    }
    leaf high-watermark {
      type uint64;
      description
        "A watermark of highest number of entries used for this resource.";
    }
    leaf last-high-watermark {
      type oc-types:timeticks64;
      description
        "The time when the high-watermark was last updated";
    }
  }

  grouping component-power-management {
    description
      "Common grouping for managing component power";
    leaf power-admin-state {
      type oc-platform-types:component-power-type;
      default "POWER_ENABLED";
      description
        "Enable or disable power to the component";
    }
  }
}
