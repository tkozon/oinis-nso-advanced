module openconfig-probes-types {
  // Generated by yanger -t ncs
  tailf:mount-id "oinis-nc-ned-nc-1.0:oinis-nc-ned-nc-1.0";
  tailf:ncs-device-type "netconf";

  yang-version 1;
  namespace "http://openconfig.net/yang/probes/types";
  prefix oc-probes-types;

  import openconfig-extensions {
    prefix oc-ext;
  }
  import tailf-common {
    prefix tailf;
  }
  import tailf-ncs {
    prefix ncs;
  }

  organization
    "OpenConfig working group";
  contact
    "OpenConfig working group
     www.openconfig.net";
  description
    "This module defines types related to the probes.";
  oc-ext:openconfig-version "0.1.1";

  revision 2018-11-21 {
    description
      "Add OpenConfig module metadata extensions.";
    reference "0.1.1";
  }
  revision 2017-09-05 {
    description
      "Initial public revision";
    reference "0.1.0";
  }
  oc-ext:regexp-posix;
  oc-ext:catalog-organization "openconfig";
  oc-ext:origin "openconfig";

  typedef ncs_compliance_template_test-type {
    type string;
    description
      "Type definition with enumerations describing the basis of
       the probe test type identifier";
  }

  typedef ncs_template_test-type {
    type string;
    description
      "Type definition with enumerations describing the basis of
       the probe test type identifier";
  }

  typedef ncs_rpc_notif_test-type {
    type enumeration {
      enum "ICMP" {
        description
          "Send ICMP echo requests.";
      }
      enum "ICMP6" {
        description
          "Send ICMP6 echo requests.";
      }
      enum "ICMP_TIMESTAMP" {
        description
          "Send ICMP timestamp requests.";
      }
      enum "ICMP6_TIMESTAMP" {
        description
          "Sedn ICMP6 timestamp requests.";
      }
      enum "TCP" {
        description
          "Send TPC packets.";
      }
      enum "UDP" {
        description
          "Send UDP packets.";
      }
      enum "UDP_TIMESTAMP" {
        description
          "Send UDP packets with timestamp.";
      }
      enum "HTTP_GET" {
        description
          "Execute HTTP GET requests.";
      }
      enum "HTTP_GET_META" {
        description
          "Execute HTTP GET requests of metadata.";
      }
    }
    description
      "Type definition with enumerations describing the basis of
       the probe test type identifier";
  }

  typedef live_ncs_test-type {
    type enumeration {
      enum "ICMP" {
        description
          "Send ICMP echo requests.";
      }
      enum "ICMP6" {
        description
          "Send ICMP6 echo requests.";
      }
      enum "ICMP_TIMESTAMP" {
        description
          "Send ICMP timestamp requests.";
      }
      enum "ICMP6_TIMESTAMP" {
        description
          "Sedn ICMP6 timestamp requests.";
      }
      enum "TCP" {
        description
          "Send TPC packets.";
      }
      enum "UDP" {
        description
          "Send UDP packets.";
      }
      enum "UDP_TIMESTAMP" {
        description
          "Send UDP packets with timestamp.";
      }
      enum "HTTP_GET" {
        description
          "Execute HTTP GET requests.";
      }
      enum "HTTP_GET_META" {
        description
          "Execute HTTP GET requests of metadata.";
      }
    }
    description
      "Type definition with enumerations describing the basis of
       the probe test type identifier";
  }

  typedef test-type {
    type enumeration {
      enum "ICMP" {
        description
          "Send ICMP echo requests.";
      }
      enum "ICMP6" {
        description
          "Send ICMP6 echo requests.";
      }
      enum "ICMP_TIMESTAMP" {
        description
          "Send ICMP timestamp requests.";
      }
      enum "ICMP6_TIMESTAMP" {
        description
          "Sedn ICMP6 timestamp requests.";
      }
      enum "TCP" {
        description
          "Send TPC packets.";
      }
      enum "UDP" {
        description
          "Send UDP packets.";
      }
      enum "UDP_TIMESTAMP" {
        description
          "Send UDP packets with timestamp.";
      }
      enum "HTTP_GET" {
        description
          "Execute HTTP GET requests.";
      }
      enum "HTTP_GET_META" {
        description
          "Execute HTTP GET requests of metadata.";
      }
    }
    description
      "Type definition with enumerations describing the basis of
       the probe test type identifier";
  }
}
