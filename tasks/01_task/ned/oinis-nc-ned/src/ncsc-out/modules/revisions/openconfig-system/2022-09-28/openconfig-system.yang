module openconfig-system {
  // Generated by yanger -t ncs
  tailf:mount-id "oinis-nc-ned-nc-1.0:oinis-nc-ned-nc-1.0";
  tailf:ncs-device-type "netconf";

  yang-version 1;
  namespace "http://openconfig.net/yang/system";
  prefix oc-sys;

  import openconfig-inet-types {
    prefix oc-inet;
  }
  import openconfig-yang-types {
    prefix oc-yang;
  }
  import openconfig-types {
    prefix oc-types;
  }
  import openconfig-extensions {
    prefix oc-ext;
  }
  import openconfig-aaa {
    prefix oc-aaa;
  }
  import openconfig-system-logging {
    prefix oc-log;
  }
  import openconfig-system-terminal {
    prefix oc-sys-term;
  }
  import openconfig-procmon {
    prefix oc-proc;
  }
  import openconfig-platform {
    prefix oc-platform;
  }
  import openconfig-alarms {
    prefix oc-alarms;
  }
  import openconfig-messages {
    prefix oc-messages;
  }
  import openconfig-license {
    prefix oc-license;
  }
  import tailf-common {
    prefix tailf;
  }
  import tailf-ncs {
    prefix ncs;
  }

  organization
    "OpenConfig working group";
  contact
    "OpenConfig working group
     netopenconfig@googlegroups.com";
  description
    "Model for managing system-wide services and functions on
     network devices.

     Portions of this code were derived from IETF RFC 7317.
     Please reproduce this note if possible.

     IETF code is subject to the following copyright and license:
     Copyright (c) IETF Trust and the persons identified as authors of
     the code.
     All rights reserved.

     Redistribution and use in source and binary forms, with or without
     modification, is permitted pursuant to, and subject to the license
     terms contained in, the Simplified BSD License set forth in
     Section 4.c of the IETF Trust's Legal Provisions Relating
     to IETF Documents (http://trustee.ietf.org/license-info).";
  oc-ext:openconfig-version "0.16.0";

  revision 2022-09-28 {
    description
      "Add last configuration timestamp leaf.";
    reference "0.16.0";
  }
  revision 2022-07-25 {
    description
      "Add system software version.";
    reference "0.15.0";
  }
  revision 2022-07-20 {
    description
      "Added routing-mac system MAC address.";
    reference "0.14.0";
  }
  revision 2022-07-12 {
    description
      "Modify ntp enabled description to reflect true and false case.";
    reference "0.13.1";
  }
  revision 2021-07-20 {
    description
      "Adding list of mount points.";
    reference "0.13.0";
  }
  revision 2021-07-14 {
    description
      "Support for additional RAM usage counters.";
    reference "0.12.0";
  }
  revision 2021-06-28 {
    description
      "Adding system memory error counters.";
    reference "0.11.1";
  }
  revision 2021-06-16 {
    description
      "Remove trailing whitespace";
    reference "0.10.1";
  }
  revision 2020-04-13 {
    description
      "Remove the existing grpc-service, and add a new list
       of the gRPC servers in a new module.";
    reference "0.10.0";
  }
  revision 2020-03-25 {
    description
      "Fix typo in description statement for ipv4-address
       list.";
    reference "0.9.1";
  }
  revision 2020-01-07 {
    description
      "Add import of license management model.";
    reference "0.9.0";
  }
  revision 2019-03-15 {
    description
      "Update boot time to be nanoseconds since epoch.";
    reference "0.8.0";
  }
  revision 2019-01-29 {
    description
      "Add messages module to the system model";
    reference "0.7.0";
  }
  revision 2018-11-21 {
    description
      "Add OpenConfig module metadata extensions.";
    reference "0.6.1";
  }
  revision 2018-07-17 {
    description
      "Add gRPC server data";
    reference "0.6.0";
  }
  revision 2018-01-21 {
    description
      "Add cpu utilization data";
    reference "0.5.0";
  }
  revision 2017-12-15 {
    description
      "Add alarms to the system model";
    reference "0.4.0";
  }
  revision 2017-09-18 {
    description
      "Updated to use OpenConfig types modules";
    reference "0.3.0";
  }
  revision 2017-07-06 {
    description
      "Move to oc-inet types, add IETF attribution, add RADIUS
       counters, changed password leaf names to indicate hashed";
    reference "0.2.0";
  }
  revision 2017-01-29 {
    description
      "Initial public release";
    reference "0.1.0";
  }
  oc-ext:regexp-posix;
  oc-ext:catalog-organization "openconfig";
  oc-ext:origin "openconfig";

  typedef ncs_compliance_template_timezone-name-type {
    type string;
    description
      "A time zone name as used by the Time Zone Database,
       sometimes referred to as the 'Olson Database'.

       The exact set of valid values is an implementation-specific
       matter.  Client discovery of the exact set of time zone names
       for a particular server is out of scope.";
    reference "BCP 175: Procedures for Maintaining the Time Zone Database";
  }

  typedef ncs_template_timezone-name-type {
    type string;
    description
      "A time zone name as used by the Time Zone Database,
       sometimes referred to as the 'Olson Database'.

       The exact set of valid values is an implementation-specific
       matter.  Client discovery of the exact set of time zone names
       for a particular server is out of scope.";
    reference "BCP 175: Procedures for Maintaining the Time Zone Database";
  }

  typedef ncs_rpc_notif_timezone-name-type {
    type string;
    description
      "A time zone name as used by the Time Zone Database,
       sometimes referred to as the 'Olson Database'.

       The exact set of valid values is an implementation-specific
       matter.  Client discovery of the exact set of time zone names
       for a particular server is out of scope.";
    reference "BCP 175: Procedures for Maintaining the Time Zone Database";
  }

  typedef live_ncs_timezone-name-type {
    type string;
    description
      "A time zone name as used by the Time Zone Database,
       sometimes referred to as the 'Olson Database'.

       The exact set of valid values is an implementation-specific
       matter.  Client discovery of the exact set of time zone names
       for a particular server is out of scope.";
    reference "BCP 175: Procedures for Maintaining the Time Zone Database";
  }

  typedef timezone-name-type {
    type string;
    description
      "A time zone name as used by the Time Zone Database,
       sometimes referred to as the 'Olson Database'.

       The exact set of valid values is an implementation-specific
       matter.  Client discovery of the exact set of time zone names
       for a particular server is out of scope.";
    reference "BCP 175: Procedures for Maintaining the Time Zone Database";
  }

  grouping ncs_compliance_template_system-clock-config {
    description
      "Configuration data for system-wide clock configuration";
    leaf timezone-name {
      type ncs_compliance_template_timezone-name-type;
      description
        "The TZ database name to use for the system, such
         as 'Europe/Stockholm'.";
      reference
        "IANA Time Zone Database
         http://www.iana.org/time-zones";
    }
  }

  grouping ncs_compliance_template_system-clock-state {
    description
      "Operational state data for system-wide clock configuration";
  }

  grouping ncs_compliance_template_system-clock-top {
    description
      "Top-level grouping for system-wide clock configuration";
    container clock {
      description
        "Top-level container for clock configuration data";
      container config {
        description
          "Configuration data for system clock";
        uses ncs_compliance_template_system-clock-config;
      }
      // NCS drop config false container state
    }
  }

  grouping ncs_compliance_template_system-global-config {
    description
      "system-wide configuration parameters";
    leaf hostname {
      type oc-inet:ncs_compliance_template_domain-name;
      description
        "The hostname of the device -- should be a single domain
         label, without the domain.";
    }
    leaf domain-name {
      type oc-inet:ncs_compliance_template_domain-name;
      description
        "Specifies the domain name used to form fully qualified name
         for unqualified hostnames.";
    }
    leaf login-banner {
      type string;
      description
        "The console login message displayed before the login prompt,
         i.e., before a user logs into the system.";
    }
    leaf motd-banner {
      type string;
      description
        "The console message displayed after a user logs into the
         system.  They system may append additional standard
         information such as the current system date and time, uptime,
         last login timestamp, etc.";
    }
  }

  grouping ncs_compliance_template_mount-point-state {
    description
      "Operational state data for the mount point.";
    leaf name {
      type string;
      description
        "Mount point name.";
    }
    leaf storage-component {
      type string;
      description
        "In the case that the filesystem that is mounted corresponds to a
         physical or logical component within the system, this leaf provides
         a reference to the hosting component within the /components
         hierarchy.

         The reference should be to the most specific component (e.g., if an
         entry for /dev/sda1 exists, then this should be referred to,
         otherwise a reference to /dev/sda may be provided.";
    }
    leaf size {
      type string;
      units "megabytes";
      description
        "The total size of the initialised filesystem.";
    }
    leaf available {
      type string;
      units "megabytes";
      description
        "The amount of unused space on the filesystem.";
    }
    leaf utilized {
      type string;
      units "megabytes";
      description
        "The amount of space currently in use on the filesystem.";
    }
  }

  grouping ncs_compliance_template_system-global-state {
    description
      "Global operational state data for the system";
    leaf current-datetime {
      type oc-yang:ncs_compliance_template_date-and-time;
      description
        "The current system date and time.";
    }
    leaf boot-time {
      type oc-types:ncs_compliance_template_timeticks64;
      units "nanoseconds";
      description
        "This timestamp indicates the time that the system was last
         restarted.  The value is the timestamp in nanoseconds relative
         to the Unix Epoch (Jan 1, 1970 00:00:00 UTC).";
    }
    leaf software-version {
      type string;
      description
        "Operating system version of the currently active controller
         of the device.  It is required that this value matches the
         value of the state/software-version leaf in the component
         of type OPERATING_SYSTEM.";
    }
    leaf last-configuration-timestamp {
      type oc-types:ncs_compliance_template_timeticks64;
      units "nanoseconds";
      description
        "Indicates the monotonically increasing timestamp at which the
         last configuration change was made. This may may be through CLI,
         gNMI or some other mechanism.";
    }
  }

  grouping ncs_compliance_template_mount-points-top {
    description
      "Top-level grouping for mount points data.";
    // NCS drop config false container 'mount-points'
  }

  grouping ncs_compliance_template_system-dns-config {
    description
      "DNS / resolver related configuration data";
    leaf-list search {
      // NCS patched for predictable order
      ordered-by user;
      type oc-inet:ncs_compliance_template_domain-name;
      description
        "An ordered list of domains to search when resolving
         a host name.";
    }
  }

  grouping ncs_compliance_template_system-dns-state {
    description
      "Operational state data for system DNS resolver";
  }

  grouping ncs_compliance_template_system-dns-servers-config {
    description
      "Configuration data for DNS resolvers";
    leaf address {
      type oc-inet:ncs_compliance_template_ip-address;
      description
        "The address of the DNS server, can be either IPv4
         or IPv6.";
    }
    leaf port {
      type oc-inet:ncs_compliance_template_port-number;
      // NCS drop default statement
      description
        "The port number of the DNS server.";
    }
  }

  grouping ncs_compliance_template_system-dns-static-config {
    description
      "Configuration data for static host entries";
    leaf hostname {
      type string;
      description
        "Hostname for the static DNS entry";
    }
    leaf-list alias {
      // NCS patched for predictable order
      ordered-by user;
      type string;
      description
        "Additional aliases for the hostname";
    }
    leaf-list ipv4-address {
      // NCS patched for predictable order
      ordered-by user;
      type oc-inet:ncs_compliance_template_ipv4-address;
      description
        "List of IPv4 addresses for the host entry";
    }
    leaf-list ipv6-address {
      // NCS patched for predictable order
      ordered-by user;
      type oc-inet:ncs_compliance_template_ipv6-address;
      description
        "List of IPv6 addresses for the host entry";
    }
  }

  grouping ncs_compliance_template_system-dns-static-state {
    description
      "Operational state data for static host entries";
  }

  grouping ncs_compliance_template_system-dns-static-top {
    description
      "Top-level grouping for static DNS host entries";
    container host-entries {
      description
        "Enclosing container for list of static host entries";
      list host-entry {
        // NCS patched for predictable order
        ordered-by user;
        key "hostname";
        description
          "List of static host entries";
        leaf hostname {
          type string;
          description
            "Reference to the hostname list key";
        }
        container config {
          description
            "Configuration data for static host entries";
          uses ncs_compliance_template_system-dns-static-config;
        }
        // NCS drop config false container state
      }
    }
  }

  grouping ncs_compliance_template_system-dns-servers-state {
    description
      "Operational state data for DNS resolvers";
  }

  grouping ncs_compliance_template_system-dns-servers-top {
    description
      "Top-level grouping for the list of DNS resolvers.";
    container servers {
      description
        "Enclosing container for DNS resolver list";
      list server {
        // NCS patched for predictable order
        ordered-by user;
        key "address";
        description
          "List of the DNS servers that the resolver should query.

           When the resolver is invoked by a calling application, it
           sends the query to the first name server in this list.  If
           no response has been received within 'timeout' seconds,
           the resolver continues with the next server in the list.
           If no response is received from any server, the resolver
           continues with the first server again.  When the resolver
           has traversed the list 'attempts' times without receiving
           any response, it gives up and returns an error to the
           calling application.

           Implementations MAY limit the number of entries in this
           list.";
        leaf address {
          type string;
          description
            "References the configured address of the DNS server";
        }
        container config {
          description
            "Configuration data for each DNS resolver";
          uses ncs_compliance_template_system-dns-servers-config;
        }
        // NCS drop config false container state
      }
    }
  }

  grouping ncs_compliance_template_system-dns-top {
    description
      "Top-level grouping for DNS / resolver config and operational
       state data";
    container dns {
      description
        "Enclosing container for DNS resolver data";
      container config {
        description
          "Configuration data for the DNS resolver";
        uses ncs_compliance_template_system-dns-config;
      }
      // NCS drop config false container state
      uses ncs_compliance_template_system-dns-servers-top;
      uses ncs_compliance_template_system-dns-static-top;
    }
  }

  grouping ncs_compliance_template_system-ntp-server-config {
    description
      "Configuration data for NTP servers";
    leaf address {
      type oc-inet:ncs_compliance_template_host;
      description
        "The address or hostname of the NTP server.";
    }
    leaf port {
      type oc-inet:ncs_compliance_template_port-number;
      // NCS drop default statement
      description
        "The port number of the NTP server.";
    }
    leaf version {
      type string;
      // NCS drop default statement
      description
        "Version number to put in outgoing NTP packets";
    }
    leaf association-type {
      type string;
      // NCS drop default statement
      description
        "The desired association type for this NTP server.";
    }
    leaf iburst {
      type string;
      // NCS drop default statement
      description
        "Indicates whether this server should enable burst
         synchronization or not.";
    }
    leaf prefer {
      type string;
      // NCS drop default statement
      description
        "Indicates whether this server should be preferred
         or not.";
    }
  }

  grouping ncs_compliance_template_system-ntp-server-state {
    description
      "Operational state data for NTP servers";
    leaf stratum {
      type string;
      description
        "Indicates the level of the server in the NTP hierarchy. As
         stratum number increases, the accuracy is degraded.  Primary
         servers are stratum while a maximum value of 16 indicates
         unsynchronized.  The values have the following specific
         semantics:

         | 0      | unspecified or invalid
         | 1      | primary server (e.g., equipped with a GPS receiver)
         | 2-15   | secondary server (via NTP)
         | 16     | unsynchronized
         | 17-255 | reserved";
      reference
        "RFC 5905 - Network Time Protocol Version 4: Protocol and
         Algorithms Specification";
    }
    leaf root-delay {
      type string;
      units "milliseconds";
      description
        "The round-trip delay to the server, in milliseconds.";
      reference
        "RFC 5905 - Network Time Protocol Version 4: Protocol and
         Algorithms Specification";
    }
    leaf root-dispersion {
      type string;
      units "milliseconds";
      description
        "Dispersion (epsilon) represents the maximum error inherent
         in the measurement";
      reference
        "RFC 5905 - Network Time Protocol Version 4: Protocol and
         Algorithms Specification";
    }
    leaf offset {
      type string;
      units "milliseconds";
      description
        "Estimate of the current time offset from the peer.  This is
         the time difference between the local and reference clock.";
    }
    leaf poll-interval {
      type string;
      units "seconds";
      description
        "Polling interval of the peer";
    }
  }

  grouping ncs_compliance_template_system-ntp-server-top {
    description
      "Top-level grouping for the list of NTP servers";
    container servers {
      description
        "Enclosing container for the list of NTP servers";
      list server {
        // NCS patched for predictable order
        ordered-by user;
        key "address";
        description
          "List of NTP servers to use for system clock
           synchronization.  If '/system/ntp/enabled'
           is 'true', then the system will attempt to
           contact and utilize the specified NTP servers.";
        leaf address {
          type string;
          description
            "References the configured address or hostname of the
             NTP server.";
        }
        container config {
          description
            "Configuration data for an NTP server.";
          uses ncs_compliance_template_system-ntp-server-config;
        }
        // NCS drop config false container state
      }
    }
  }

  grouping ncs_compliance_template_system-ntp-auth-keys-config {
    description
      "Configuration data ";
    leaf key-id {
      type string;
      description
        "Integer identifier used by the client and server to
         designate a secret key.  The client and server must use
         the same key id.";
    }
    leaf key-type {
      type string;
      description
        "Encryption type used for the NTP authentication key";
    }
    leaf key-value {
      type string;
      description
        "NTP authentication key value";
    }
  }

  grouping ncs_compliance_template_system-ntp-auth-keys-state {
    description
      "Operational state data for NTP auth key data";
  }

  grouping ncs_compliance_template_system-ntp-auth-keys-top {
    description
      "Top-level grouping for NTP auth key data";
    container ntp-keys {
      description
        "Enclosing container for list of NTP authentication keys";
      list ntp-key {
        // NCS patched for predictable order
        ordered-by user;
        key "key-id";
        description
          "List of NTP authentication keys";
        leaf key-id {
          type string;
          description
            "Reference to auth key-id list key";
        }
        container config {
          description
            "Configuration data for NTP auth keys";
          uses ncs_compliance_template_system-ntp-auth-keys-config;
        }
        // NCS drop config false container state
      }
    }
  }

  grouping ncs_compliance_template_system-ntp-config {
    description
      "Configuration data for system-wide NTP operation.";
    leaf enabled {
      type string;
      // NCS drop default statement
      description
        "Enables and disables the NTP protocol and indicates that the system should
         attempt to synchronize the system clock with an NTP server
         from the servers defined in the 'ntp/server' list.";
    }
    leaf ntp-source-address {
      type oc-inet:ncs_compliance_template_ip-address;
      description
        "Source address to use on outgoing NTP packets";
    }
    leaf enable-ntp-auth {
      type string;
      // NCS drop default statement
      description
        "Enable or disable NTP authentication -- when enabled, the
         system will only use packets containing a trusted
         authentication key to synchronize the time.";
    }
  }

  grouping ncs_compliance_template_system-ntp-state {
    description
      "Operational state data for system-wide NTP operation.";
    leaf auth-mismatch {
      type oc-yang:ncs_compliance_template_counter64;
      description
        "Count of the number of NTP packets received that were not
         processed due to authentication mismatch.";
    }
  }

  grouping ncs_compliance_template_system-ntp-top {
    description
      "Top-level grouping for configuration and state data for NTP";
    container ntp {
      description
        "Top-level container for NTP configuration and state";
      container config {
        description
          "Configuration data for NTP client.";
        uses ncs_compliance_template_system-ntp-config;
      }
      // NCS drop config false container state
      uses ncs_compliance_template_system-ntp-auth-keys-top;
      uses ncs_compliance_template_system-ntp-server-top;
    }
  }

  grouping ncs_compliance_template_system-routing-macaddr-config {
    description
      "Configuration data for system's routing MAC addresses.";
    leaf routing-mac {
      type oc-yang:ncs_compliance_template_mac-address;
      description
        "Any packets destined to this MAC address must be sent through the
         routing pipeline by the system. This MAC address is used to identify
         routed packets in addition to any other MAC addresses that the system
         may already have been using to perform routing.

         It is not expected that this MAC address will be used as the
         source MAC address of any routed packet, as the source MAC address of
         any packets generated by the system, or a MAC address used in ARP
         response. This MAC address may not be allocated from the block of
         MAC address that system owns. For instance, it's allocation could
         be managed by an external controller.";
    }
  }

  grouping ncs_compliance_template_system-macaddr-top {
    description
      "Top-level grouping for configuration and state of system's MAC addresses.";
    container mac-address {
      description
        "Top-level container for system's MAC address configuration and state";
      container config {
        description
          "Configuration data for routing MAC address.";
        uses ncs_compliance_template_system-routing-macaddr-config;
      }
      // NCS drop config false container state
    }
  }

  grouping ncs_compliance_template_system-memory-config {
    description
      "Configuration data for system memory";
  }

  grouping ncs_compliance_template_system-memory-state {
    description
      "Operational state data for system memory";
    leaf physical {
      type string;
      units "bytes";
      description
        "Reports the total physical memory available on the
         system.";
    }
    leaf reserved {
      type string;
      units "bytes";
      description
        "Memory reserved for system use";
    }
    leaf used {
      type string;
      units "bytes";
      description
        "Memory that has been used and not available for allocation.";
    }
    leaf free {
      type string;
      units "bytes";
      description
        "Memory that is not used and is available for allocation.";
    }
  }

  grouping ncs_compliance_template_system-memory-error-counters {
    description
      "Counters for system memory errors.";
    leaf correctable-ecc-errors {
      type string;
      description
        "Count of correctable ECC errors. Systems with ECC memory
         are capable of correcting Single-bit ECC errors.";
    }
    leaf uncorrectable-ecc-errors {
      type string;
      description
        "Count of uncorrectable ECC errors. Systems with ECC
         memory are capable of detecting multi-bit ECC errors,
         but cannot correct them.";
    }
    leaf total-ecc-errors {
      type string;
      description
        "Count of total ECC errors, this includes both correctable
         and uncorrectable ECC errors.";
    }
  }

  grouping ncs_compliance_template_system-memory-top {
    description
      "Top-level grouping for system memory data definitions";
    container memory {
      description
        "Top-level container for system memory data";
      container config {
        description
          "Configuration data for system memory";
        uses ncs_compliance_template_system-memory-config;
      }
      // NCS drop config false container state
    }
  }

  grouping ncs_compliance_template_system-cpu-state {
    description
      "Operational state data for the system CPU(s)";
    leaf index {
      type string;
      description
        "The CPU index for each processor core on the system.  On a
         single-core system, the index should be zero.  The ALL
         index signifies an aggregation of the CPU utilization
         statistics over all cores in the system.";
    }
    container total {
      description
        "Total CPU utilization.";
      uses oc-types:ncs_compliance_template_avg-min-max-instant-stats-pct;
    }
    container user {
      description
        "Percentage of CPU time spent running in user space.";
      uses oc-types:ncs_compliance_template_avg-min-max-instant-stats-pct;
    }
    container kernel {
      description
        "Percentage of CPU time spent running in kernel space.";
      uses oc-types:ncs_compliance_template_avg-min-max-instant-stats-pct;
    }
    container nice {
      description
        "Percentage of CPU time spent running low-priority (niced)
         user processes.";
      uses oc-types:ncs_compliance_template_avg-min-max-instant-stats-pct;
    }
    container idle {
      description
        "Percentage of CPU time spent idle.";
      uses oc-types:ncs_compliance_template_avg-min-max-instant-stats-pct;
    }
    container wait {
      description
        "Percentage of CPU time spent waiting for I/O.";
      uses oc-types:ncs_compliance_template_avg-min-max-instant-stats-pct;
    }
    container hardware-interrupt {
      description
        "Percentage of CPU time spent servicing hardware interrupts.";
      uses oc-types:ncs_compliance_template_avg-min-max-instant-stats-pct;
    }
    container software-interrupt {
      description
        "Percentage of CPU time spent servicing software interrupts";
      uses oc-types:ncs_compliance_template_avg-min-max-instant-stats-pct;
    }
  }

  grouping ncs_compliance_template_system-cpu-top {
    description
      "Top-level grouping for system CPU data";
    // NCS drop config false container cpus
  }

  grouping ncs_compliance_template_system-top {
    description
      "Top level system data containers";
    container system {
      description
        "Enclosing container for system-related configuration and
         operational state data";
      container config {
        description
          "Global configuration data for the system";
        uses ncs_compliance_template_system-global-config;
      }
      // NCS drop config false container state
      uses ncs_compliance_template_mount-points-top;
      uses ncs_compliance_template_system-clock-top;
      uses ncs_compliance_template_system-dns-top;
      uses ncs_compliance_template_system-ntp-top;
      uses oc-sys-term:ncs_compliance_template_system-ssh-server-top;
      uses oc-sys-term:ncs_compliance_template_system-telnet-server-top;
      uses oc-log:ncs_compliance_template_logging-top;
      uses oc-aaa:ncs_compliance_template_aaa-top;
      uses ncs_compliance_template_system-memory-top;
      uses ncs_compliance_template_system-cpu-top;
      uses oc-proc:ncs_compliance_template_procmon-processes-top;
      uses oc-alarms:ncs_compliance_template_alarms-top;
      uses oc-messages:ncs_compliance_template_messages-top;
      uses oc-license:ncs_compliance_template_license-top;
      uses ncs_compliance_template_system-macaddr-top;
    }
  }

  grouping ncs_template_system-clock-config {
    description
      "Configuration data for system-wide clock configuration";
    leaf timezone-name {
      type ncs_template_timezone-name-type;
      description
        "The TZ database name to use for the system, such
         as 'Europe/Stockholm'.";
      reference
        "IANA Time Zone Database
         http://www.iana.org/time-zones";
    }
  }

  grouping ncs_template_system-clock-state {
    description
      "Operational state data for system-wide clock configuration";
  }

  grouping ncs_template_system-clock-top {
    description
      "Top-level grouping for system-wide clock configuration";
    container clock {
      description
        "Top-level container for clock configuration data";
      container config {
        description
          "Configuration data for system clock";
        uses ncs_template_system-clock-config;
      }
      // NCS drop config false container state
    }
  }

  grouping ncs_template_system-global-config {
    description
      "system-wide configuration parameters";
    leaf hostname {
      type oc-inet:ncs_template_domain-name;
      description
        "The hostname of the device -- should be a single domain
         label, without the domain.";
    }
    leaf domain-name {
      type oc-inet:ncs_template_domain-name;
      description
        "Specifies the domain name used to form fully qualified name
         for unqualified hostnames.";
    }
    leaf login-banner {
      type string;
      description
        "The console login message displayed before the login prompt,
         i.e., before a user logs into the system.";
    }
    leaf motd-banner {
      type string;
      description
        "The console message displayed after a user logs into the
         system.  They system may append additional standard
         information such as the current system date and time, uptime,
         last login timestamp, etc.";
    }
  }

  grouping ncs_template_mount-point-state {
    description
      "Operational state data for the mount point.";
    leaf name {
      type string;
      description
        "Mount point name.";
    }
    leaf storage-component {
      type string;
      description
        "In the case that the filesystem that is mounted corresponds to a
         physical or logical component within the system, this leaf provides
         a reference to the hosting component within the /components
         hierarchy.

         The reference should be to the most specific component (e.g., if an
         entry for /dev/sda1 exists, then this should be referred to,
         otherwise a reference to /dev/sda may be provided.";
    }
    leaf size {
      type string;
      units "megabytes";
      description
        "The total size of the initialised filesystem.";
    }
    leaf available {
      type string;
      units "megabytes";
      description
        "The amount of unused space on the filesystem.";
    }
    leaf utilized {
      type string;
      units "megabytes";
      description
        "The amount of space currently in use on the filesystem.";
    }
  }

  grouping ncs_template_system-global-state {
    description
      "Global operational state data for the system";
    leaf current-datetime {
      type oc-yang:ncs_template_date-and-time;
      description
        "The current system date and time.";
    }
    leaf boot-time {
      type oc-types:ncs_template_timeticks64;
      units "nanoseconds";
      description
        "This timestamp indicates the time that the system was last
         restarted.  The value is the timestamp in nanoseconds relative
         to the Unix Epoch (Jan 1, 1970 00:00:00 UTC).";
    }
    leaf software-version {
      type string;
      description
        "Operating system version of the currently active controller
         of the device.  It is required that this value matches the
         value of the state/software-version leaf in the component
         of type OPERATING_SYSTEM.";
    }
    leaf last-configuration-timestamp {
      type oc-types:ncs_template_timeticks64;
      units "nanoseconds";
      description
        "Indicates the monotonically increasing timestamp at which the
         last configuration change was made. This may may be through CLI,
         gNMI or some other mechanism.";
    }
  }

  grouping ncs_template_mount-points-top {
    description
      "Top-level grouping for mount points data.";
    // NCS drop config false container 'mount-points'
  }

  grouping ncs_template_system-dns-config {
    description
      "DNS / resolver related configuration data";
    leaf-list search {
      // NCS patched for predictable order
      ordered-by user;
      type oc-inet:ncs_template_domain-name;
      description
        "An ordered list of domains to search when resolving
         a host name.";
    }
  }

  grouping ncs_template_system-dns-state {
    description
      "Operational state data for system DNS resolver";
  }

  grouping ncs_template_system-dns-servers-config {
    description
      "Configuration data for DNS resolvers";
    leaf address {
      type oc-inet:ncs_template_ip-address;
      description
        "The address of the DNS server, can be either IPv4
         or IPv6.";
    }
    leaf port {
      type oc-inet:ncs_template_port-number;
      // NCS drop default statement
      description
        "The port number of the DNS server.";
    }
  }

  grouping ncs_template_system-dns-static-config {
    description
      "Configuration data for static host entries";
    leaf hostname {
      type string;
      description
        "Hostname for the static DNS entry";
    }
    leaf-list alias {
      // NCS patched for predictable order
      ordered-by user;
      type string;
      description
        "Additional aliases for the hostname";
    }
    leaf-list ipv4-address {
      // NCS patched for predictable order
      ordered-by user;
      type oc-inet:ncs_template_ipv4-address;
      description
        "List of IPv4 addresses for the host entry";
    }
    leaf-list ipv6-address {
      // NCS patched for predictable order
      ordered-by user;
      type oc-inet:ncs_template_ipv6-address;
      description
        "List of IPv6 addresses for the host entry";
    }
  }

  grouping ncs_template_system-dns-static-state {
    description
      "Operational state data for static host entries";
  }

  grouping ncs_template_system-dns-static-top {
    description
      "Top-level grouping for static DNS host entries";
    container host-entries {
      description
        "Enclosing container for list of static host entries";
      list host-entry {
        // NCS patched for predictable order
        ordered-by user;
        key "hostname";
        description
          "List of static host entries";
        leaf hostname {
          type string;
          description
            "Reference to the hostname list key";
        }
        container config {
          description
            "Configuration data for static host entries";
          uses ncs_template_system-dns-static-config;
        }
        // NCS drop config false container state
      }
    }
  }

  grouping ncs_template_system-dns-servers-state {
    description
      "Operational state data for DNS resolvers";
  }

  grouping ncs_template_system-dns-servers-top {
    description
      "Top-level grouping for the list of DNS resolvers.";
    container servers {
      description
        "Enclosing container for DNS resolver list";
      list server {
        // NCS patched for predictable order
        ordered-by user;
        key "address";
        description
          "List of the DNS servers that the resolver should query.

           When the resolver is invoked by a calling application, it
           sends the query to the first name server in this list.  If
           no response has been received within 'timeout' seconds,
           the resolver continues with the next server in the list.
           If no response is received from any server, the resolver
           continues with the first server again.  When the resolver
           has traversed the list 'attempts' times without receiving
           any response, it gives up and returns an error to the
           calling application.

           Implementations MAY limit the number of entries in this
           list.";
        leaf address {
          type string;
          description
            "References the configured address of the DNS server";
        }
        container config {
          description
            "Configuration data for each DNS resolver";
          uses ncs_template_system-dns-servers-config;
        }
        // NCS drop config false container state
      }
    }
  }

  grouping ncs_template_system-dns-top {
    description
      "Top-level grouping for DNS / resolver config and operational
       state data";
    container dns {
      description
        "Enclosing container for DNS resolver data";
      container config {
        description
          "Configuration data for the DNS resolver";
        uses ncs_template_system-dns-config;
      }
      // NCS drop config false container state
      uses ncs_template_system-dns-servers-top;
      uses ncs_template_system-dns-static-top;
    }
  }

  grouping ncs_template_system-ntp-server-config {
    description
      "Configuration data for NTP servers";
    leaf address {
      type oc-inet:ncs_template_host;
      description
        "The address or hostname of the NTP server.";
    }
    leaf port {
      type oc-inet:ncs_template_port-number;
      // NCS drop default statement
      description
        "The port number of the NTP server.";
    }
    leaf version {
      type string;
      // NCS drop default statement
      description
        "Version number to put in outgoing NTP packets";
    }
    leaf association-type {
      type string;
      // NCS drop default statement
      description
        "The desired association type for this NTP server.";
    }
    leaf iburst {
      type string;
      // NCS drop default statement
      description
        "Indicates whether this server should enable burst
         synchronization or not.";
    }
    leaf prefer {
      type string;
      // NCS drop default statement
      description
        "Indicates whether this server should be preferred
         or not.";
    }
  }

  grouping ncs_template_system-ntp-server-state {
    description
      "Operational state data for NTP servers";
    leaf stratum {
      type string;
      description
        "Indicates the level of the server in the NTP hierarchy. As
         stratum number increases, the accuracy is degraded.  Primary
         servers are stratum while a maximum value of 16 indicates
         unsynchronized.  The values have the following specific
         semantics:

         | 0      | unspecified or invalid
         | 1      | primary server (e.g., equipped with a GPS receiver)
         | 2-15   | secondary server (via NTP)
         | 16     | unsynchronized
         | 17-255 | reserved";
      reference
        "RFC 5905 - Network Time Protocol Version 4: Protocol and
         Algorithms Specification";
    }
    leaf root-delay {
      type string;
      units "milliseconds";
      description
        "The round-trip delay to the server, in milliseconds.";
      reference
        "RFC 5905 - Network Time Protocol Version 4: Protocol and
         Algorithms Specification";
    }
    leaf root-dispersion {
      type string;
      units "milliseconds";
      description
        "Dispersion (epsilon) represents the maximum error inherent
         in the measurement";
      reference
        "RFC 5905 - Network Time Protocol Version 4: Protocol and
         Algorithms Specification";
    }
    leaf offset {
      type string;
      units "milliseconds";
      description
        "Estimate of the current time offset from the peer.  This is
         the time difference between the local and reference clock.";
    }
    leaf poll-interval {
      type string;
      units "seconds";
      description
        "Polling interval of the peer";
    }
  }

  grouping ncs_template_system-ntp-server-top {
    description
      "Top-level grouping for the list of NTP servers";
    container servers {
      description
        "Enclosing container for the list of NTP servers";
      list server {
        // NCS patched for predictable order
        ordered-by user;
        key "address";
        description
          "List of NTP servers to use for system clock
           synchronization.  If '/system/ntp/enabled'
           is 'true', then the system will attempt to
           contact and utilize the specified NTP servers.";
        leaf address {
          type string;
          description
            "References the configured address or hostname of the
             NTP server.";
        }
        container config {
          description
            "Configuration data for an NTP server.";
          uses ncs_template_system-ntp-server-config;
        }
        // NCS drop config false container state
      }
    }
  }

  grouping ncs_template_system-ntp-auth-keys-config {
    description
      "Configuration data ";
    leaf key-id {
      type string;
      description
        "Integer identifier used by the client and server to
         designate a secret key.  The client and server must use
         the same key id.";
    }
    leaf key-type {
      type string;
      description
        "Encryption type used for the NTP authentication key";
    }
    leaf key-value {
      type string;
      description
        "NTP authentication key value";
    }
  }

  grouping ncs_template_system-ntp-auth-keys-state {
    description
      "Operational state data for NTP auth key data";
  }

  grouping ncs_template_system-ntp-auth-keys-top {
    description
      "Top-level grouping for NTP auth key data";
    container ntp-keys {
      description
        "Enclosing container for list of NTP authentication keys";
      list ntp-key {
        // NCS patched for predictable order
        ordered-by user;
        key "key-id";
        description
          "List of NTP authentication keys";
        leaf key-id {
          type string;
          description
            "Reference to auth key-id list key";
        }
        container config {
          description
            "Configuration data for NTP auth keys";
          uses ncs_template_system-ntp-auth-keys-config;
        }
        // NCS drop config false container state
      }
    }
  }

  grouping ncs_template_system-ntp-config {
    description
      "Configuration data for system-wide NTP operation.";
    leaf enabled {
      type string;
      // NCS drop default statement
      description
        "Enables and disables the NTP protocol and indicates that the system should
         attempt to synchronize the system clock with an NTP server
         from the servers defined in the 'ntp/server' list.";
    }
    leaf ntp-source-address {
      type oc-inet:ncs_template_ip-address;
      description
        "Source address to use on outgoing NTP packets";
    }
    leaf enable-ntp-auth {
      type string;
      // NCS drop default statement
      description
        "Enable or disable NTP authentication -- when enabled, the
         system will only use packets containing a trusted
         authentication key to synchronize the time.";
    }
  }

  grouping ncs_template_system-ntp-state {
    description
      "Operational state data for system-wide NTP operation.";
    leaf auth-mismatch {
      type oc-yang:ncs_template_counter64;
      description
        "Count of the number of NTP packets received that were not
         processed due to authentication mismatch.";
    }
  }

  grouping ncs_template_system-ntp-top {
    description
      "Top-level grouping for configuration and state data for NTP";
    container ntp {
      description
        "Top-level container for NTP configuration and state";
      container config {
        description
          "Configuration data for NTP client.";
        uses ncs_template_system-ntp-config;
      }
      // NCS drop config false container state
      uses ncs_template_system-ntp-auth-keys-top;
      uses ncs_template_system-ntp-server-top;
    }
  }

  grouping ncs_template_system-routing-macaddr-config {
    description
      "Configuration data for system's routing MAC addresses.";
    leaf routing-mac {
      type oc-yang:ncs_template_mac-address;
      description
        "Any packets destined to this MAC address must be sent through the
         routing pipeline by the system. This MAC address is used to identify
         routed packets in addition to any other MAC addresses that the system
         may already have been using to perform routing.

         It is not expected that this MAC address will be used as the
         source MAC address of any routed packet, as the source MAC address of
         any packets generated by the system, or a MAC address used in ARP
         response. This MAC address may not be allocated from the block of
         MAC address that system owns. For instance, it's allocation could
         be managed by an external controller.";
    }
  }

  grouping ncs_template_system-macaddr-top {
    description
      "Top-level grouping for configuration and state of system's MAC addresses.";
    container mac-address {
      description
        "Top-level container for system's MAC address configuration and state";
      container config {
        description
          "Configuration data for routing MAC address.";
        uses ncs_template_system-routing-macaddr-config;
      }
      // NCS drop config false container state
    }
  }

  grouping ncs_template_system-memory-config {
    description
      "Configuration data for system memory";
  }

  grouping ncs_template_system-memory-state {
    description
      "Operational state data for system memory";
    leaf physical {
      type string;
      units "bytes";
      description
        "Reports the total physical memory available on the
         system.";
    }
    leaf reserved {
      type string;
      units "bytes";
      description
        "Memory reserved for system use";
    }
    leaf used {
      type string;
      units "bytes";
      description
        "Memory that has been used and not available for allocation.";
    }
    leaf free {
      type string;
      units "bytes";
      description
        "Memory that is not used and is available for allocation.";
    }
  }

  grouping ncs_template_system-memory-error-counters {
    description
      "Counters for system memory errors.";
    leaf correctable-ecc-errors {
      type string;
      description
        "Count of correctable ECC errors. Systems with ECC memory
         are capable of correcting Single-bit ECC errors.";
    }
    leaf uncorrectable-ecc-errors {
      type string;
      description
        "Count of uncorrectable ECC errors. Systems with ECC
         memory are capable of detecting multi-bit ECC errors,
         but cannot correct them.";
    }
    leaf total-ecc-errors {
      type string;
      description
        "Count of total ECC errors, this includes both correctable
         and uncorrectable ECC errors.";
    }
  }

  grouping ncs_template_system-memory-top {
    description
      "Top-level grouping for system memory data definitions";
    container memory {
      description
        "Top-level container for system memory data";
      container config {
        description
          "Configuration data for system memory";
        uses ncs_template_system-memory-config;
      }
      // NCS drop config false container state
    }
  }

  grouping ncs_template_system-cpu-state {
    description
      "Operational state data for the system CPU(s)";
    leaf index {
      type string;
      description
        "The CPU index for each processor core on the system.  On a
         single-core system, the index should be zero.  The ALL
         index signifies an aggregation of the CPU utilization
         statistics over all cores in the system.";
    }
    container total {
      description
        "Total CPU utilization.";
      uses oc-types:ncs_template_avg-min-max-instant-stats-pct;
    }
    container user {
      description
        "Percentage of CPU time spent running in user space.";
      uses oc-types:ncs_template_avg-min-max-instant-stats-pct;
    }
    container kernel {
      description
        "Percentage of CPU time spent running in kernel space.";
      uses oc-types:ncs_template_avg-min-max-instant-stats-pct;
    }
    container nice {
      description
        "Percentage of CPU time spent running low-priority (niced)
         user processes.";
      uses oc-types:ncs_template_avg-min-max-instant-stats-pct;
    }
    container idle {
      description
        "Percentage of CPU time spent idle.";
      uses oc-types:ncs_template_avg-min-max-instant-stats-pct;
    }
    container wait {
      description
        "Percentage of CPU time spent waiting for I/O.";
      uses oc-types:ncs_template_avg-min-max-instant-stats-pct;
    }
    container hardware-interrupt {
      description
        "Percentage of CPU time spent servicing hardware interrupts.";
      uses oc-types:ncs_template_avg-min-max-instant-stats-pct;
    }
    container software-interrupt {
      description
        "Percentage of CPU time spent servicing software interrupts";
      uses oc-types:ncs_template_avg-min-max-instant-stats-pct;
    }
  }

  grouping ncs_template_system-cpu-top {
    description
      "Top-level grouping for system CPU data";
    // NCS drop config false container cpus
  }

  grouping ncs_template_system-top {
    description
      "Top level system data containers";
    container system {
      description
        "Enclosing container for system-related configuration and
         operational state data";
      container config {
        description
          "Global configuration data for the system";
        uses ncs_template_system-global-config;
      }
      // NCS drop config false container state
      uses ncs_template_mount-points-top;
      uses ncs_template_system-clock-top;
      uses ncs_template_system-dns-top;
      uses ncs_template_system-ntp-top;
      uses oc-sys-term:ncs_template_system-ssh-server-top;
      uses oc-sys-term:ncs_template_system-telnet-server-top;
      uses oc-log:ncs_template_logging-top;
      uses oc-aaa:ncs_template_aaa-top;
      uses ncs_template_system-memory-top;
      uses ncs_template_system-cpu-top;
      uses oc-proc:ncs_template_procmon-processes-top;
      uses oc-alarms:ncs_template_alarms-top;
      uses oc-messages:ncs_template_messages-top;
      uses oc-license:ncs_template_license-top;
      uses ncs_template_system-macaddr-top;
    }
  }

  grouping ncs_rpc_notif_system-clock-config {
    description
      "Configuration data for system-wide clock configuration";
    leaf timezone-name {
      type ncs_rpc_notif_timezone-name-type;
      description
        "The TZ database name to use for the system, such
         as 'Europe/Stockholm'.";
      reference
        "IANA Time Zone Database
         http://www.iana.org/time-zones";
    }
  }

  grouping ncs_rpc_notif_system-clock-state {
    description
      "Operational state data for system-wide clock configuration";
  }

  grouping ncs_rpc_notif_system-clock-top {
    description
      "Top-level grouping for system-wide clock configuration";
    container clock {
      description
        "Top-level container for clock configuration data";
      container config {
        description
          "Configuration data for system clock";
        uses ncs_rpc_notif_system-clock-config;
      }
      container state {
        config false;
        description
          "Operational state data for system clock";
        uses ncs_rpc_notif_system-clock-config;
        uses ncs_rpc_notif_system-clock-state;
      }
    }
  }

  grouping ncs_rpc_notif_system-global-config {
    description
      "system-wide configuration parameters";
    leaf hostname {
      type oc-inet:ncs_rpc_notif_domain-name;
      description
        "The hostname of the device -- should be a single domain
         label, without the domain.";
    }
    leaf domain-name {
      type oc-inet:ncs_rpc_notif_domain-name;
      description
        "Specifies the domain name used to form fully qualified name
         for unqualified hostnames.";
    }
    leaf login-banner {
      type string;
      description
        "The console login message displayed before the login prompt,
         i.e., before a user logs into the system.";
    }
    leaf motd-banner {
      type string;
      description
        "The console message displayed after a user logs into the
         system.  They system may append additional standard
         information such as the current system date and time, uptime,
         last login timestamp, etc.";
    }
  }

  grouping ncs_rpc_notif_mount-point-state {
    description
      "Operational state data for the mount point.";
    leaf name {
      type string;
      description
        "Mount point name.";
    }
    leaf storage-component {
      type string;
      description
        "In the case that the filesystem that is mounted corresponds to a
         physical or logical component within the system, this leaf provides
         a reference to the hosting component within the /components
         hierarchy.

         The reference should be to the most specific component (e.g., if an
         entry for /dev/sda1 exists, then this should be referred to,
         otherwise a reference to /dev/sda may be provided.";
    }
    leaf size {
      type uint64;
      units "megabytes";
      description
        "The total size of the initialised filesystem.";
    }
    leaf available {
      type uint64;
      units "megabytes";
      description
        "The amount of unused space on the filesystem.";
    }
    leaf utilized {
      type uint64;
      units "megabytes";
      description
        "The amount of space currently in use on the filesystem.";
    }
  }

  grouping ncs_rpc_notif_system-global-state {
    description
      "Global operational state data for the system";
    leaf current-datetime {
      type oc-yang:ncs_rpc_notif_date-and-time;
      description
        "The current system date and time.";
    }
    leaf boot-time {
      type oc-types:ncs_rpc_notif_timeticks64;
      units "nanoseconds";
      description
        "This timestamp indicates the time that the system was last
         restarted.  The value is the timestamp in nanoseconds relative
         to the Unix Epoch (Jan 1, 1970 00:00:00 UTC).";
    }
    leaf software-version {
      type string;
      description
        "Operating system version of the currently active controller
         of the device.  It is required that this value matches the
         value of the state/software-version leaf in the component
         of type OPERATING_SYSTEM.";
    }
    leaf last-configuration-timestamp {
      type oc-types:ncs_rpc_notif_timeticks64;
      units "nanoseconds";
      description
        "Indicates the monotonically increasing timestamp at which the
         last configuration change was made. This may may be through CLI,
         gNMI or some other mechanism.";
    }
  }

  grouping ncs_rpc_notif_mount-points-top {
    description
      "Top-level grouping for mount points data.";
    container mount-points {
      config false;
      description
        "When a system has a set of filesystems that are attached to a
         directory (i.e., mounted on the system) they are expected to be
         present in this list. If the system has the concept of mounting
         physical or virtual resources to a mount point within the root
         filesystem (/) they should also be included in this list.";
      list mount-point {
        key "name";
        description
          "List of mount points in the system.";
        leaf name {
          type leafref {
            path "../state/name";
          }
          description
            "Reference to the key for list of mount points.";
        }
        container state {
          config false;
          description
            "State of system mount point.";
          uses ncs_rpc_notif_mount-point-state;
        }
      }
    }
  }

  grouping ncs_rpc_notif_system-dns-config {
    description
      "DNS / resolver related configuration data";
    leaf-list search {
      type oc-inet:ncs_rpc_notif_domain-name;
      ordered-by user;
      description
        "An ordered list of domains to search when resolving
         a host name.";
    }
  }

  grouping ncs_rpc_notif_system-dns-state {
    description
      "Operational state data for system DNS resolver";
  }

  grouping ncs_rpc_notif_system-dns-servers-config {
    description
      "Configuration data for DNS resolvers";
    leaf address {
      type oc-inet:ncs_rpc_notif_ip-address;
      description
        "The address of the DNS server, can be either IPv4
         or IPv6.";
    }
    leaf port {
      type oc-inet:ncs_rpc_notif_port-number;
      default "53";
      description
        "The port number of the DNS server.";
    }
  }

  grouping ncs_rpc_notif_system-dns-static-config {
    description
      "Configuration data for static host entries";
    leaf hostname {
      type string;
      description
        "Hostname for the static DNS entry";
    }
    leaf-list alias {
      type string;
      description
        "Additional aliases for the hostname";
    }
    leaf-list ipv4-address {
      type oc-inet:ncs_rpc_notif_ipv4-address;
      description
        "List of IPv4 addresses for the host entry";
    }
    leaf-list ipv6-address {
      type oc-inet:ncs_rpc_notif_ipv6-address;
      description
        "List of IPv6 addresses for the host entry";
    }
  }

  grouping ncs_rpc_notif_system-dns-static-state {
    description
      "Operational state data for static host entries";
  }

  grouping ncs_rpc_notif_system-dns-static-top {
    description
      "Top-level grouping for static DNS host entries";
    container host-entries {
      description
        "Enclosing container for list of static host entries";
      list host-entry {
        key "hostname";
        description
          "List of static host entries";
        leaf hostname {
          type leafref {
            path "../config/hostname";
          }
          description
            "Reference to the hostname list key";
        }
        container config {
          description
            "Configuration data for static host entries";
          uses ncs_rpc_notif_system-dns-static-config;
        }
        container state {
          config false;
          description
            "Operational state data for static host entries";
          uses ncs_rpc_notif_system-dns-static-config;
          uses ncs_rpc_notif_system-dns-static-state;
        }
      }
    }
  }

  grouping ncs_rpc_notif_system-dns-servers-state {
    description
      "Operational state data for DNS resolvers";
  }

  grouping ncs_rpc_notif_system-dns-servers-top {
    description
      "Top-level grouping for the list of DNS resolvers.";
    container servers {
      description
        "Enclosing container for DNS resolver list";
      list server {
        key "address";
        ordered-by user;
        description
          "List of the DNS servers that the resolver should query.

           When the resolver is invoked by a calling application, it
           sends the query to the first name server in this list.  If
           no response has been received within 'timeout' seconds,
           the resolver continues with the next server in the list.
           If no response is received from any server, the resolver
           continues with the first server again.  When the resolver
           has traversed the list 'attempts' times without receiving
           any response, it gives up and returns an error to the
           calling application.

           Implementations MAY limit the number of entries in this
           list.";
        leaf address {
          type leafref {
            path "../config/address";
          }
          description
            "References the configured address of the DNS server";
        }
        container config {
          description
            "Configuration data for each DNS resolver";
          uses ncs_rpc_notif_system-dns-servers-config;
        }
        container state {
          config false;
          description
            "Operational state data for each DNS resolver";
          uses ncs_rpc_notif_system-dns-servers-config;
          uses ncs_rpc_notif_system-dns-servers-state;
        }
      }
    }
  }

  grouping ncs_rpc_notif_system-dns-top {
    description
      "Top-level grouping for DNS / resolver config and operational
       state data";
    container dns {
      description
        "Enclosing container for DNS resolver data";
      container config {
        description
          "Configuration data for the DNS resolver";
        uses ncs_rpc_notif_system-dns-config;
      }
      container state {
        config false;
        description
          "Operational state data for the DNS resolver";
        uses ncs_rpc_notif_system-dns-config;
        uses ncs_rpc_notif_system-dns-state;
      }
      uses ncs_rpc_notif_system-dns-servers-top;
      uses ncs_rpc_notif_system-dns-static-top;
    }
  }

  grouping ncs_rpc_notif_system-ntp-server-config {
    description
      "Configuration data for NTP servers";
    leaf address {
      type oc-inet:ncs_rpc_notif_host;
      description
        "The address or hostname of the NTP server.";
    }
    leaf port {
      type oc-inet:ncs_rpc_notif_port-number;
      default "123";
      description
        "The port number of the NTP server.";
    }
    leaf version {
      type uint8 {
        range "1..4";
      }
      default "4";
      description
        "Version number to put in outgoing NTP packets";
    }
    leaf association-type {
      type enumeration {
        enum "SERVER" {
          description
            "Use client association mode.  This device
             will not provide synchronization to the
             configured NTP server.";
        }
        enum "PEER" {
          description
            "Use symmetric active association mode.
             This device may provide synchronization
             to the configured NTP server.";
        }
        enum "POOL" {
          description
            "Use client association mode with one or
             more of the NTP servers found by DNS
             resolution of the domain name given by
             the 'address' leaf.  This device will not
             provide synchronization to the servers.";
        }
      }
      default "SERVER";
      description
        "The desired association type for this NTP server.";
    }
    leaf iburst {
      type boolean;
      default "false";
      description
        "Indicates whether this server should enable burst
         synchronization or not.";
    }
    leaf prefer {
      type boolean;
      default "false";
      description
        "Indicates whether this server should be preferred
         or not.";
    }
  }

  grouping ncs_rpc_notif_system-ntp-server-state {
    description
      "Operational state data for NTP servers";
    leaf stratum {
      type uint8;
      description
        "Indicates the level of the server in the NTP hierarchy. As
         stratum number increases, the accuracy is degraded.  Primary
         servers are stratum while a maximum value of 16 indicates
         unsynchronized.  The values have the following specific
         semantics:

         | 0      | unspecified or invalid
         | 1      | primary server (e.g., equipped with a GPS receiver)
         | 2-15   | secondary server (via NTP)
         | 16     | unsynchronized
         | 17-255 | reserved";
      reference
        "RFC 5905 - Network Time Protocol Version 4: Protocol and
         Algorithms Specification";
    }
    leaf root-delay {
      type uint32;
      units "milliseconds";
      description
        "The round-trip delay to the server, in milliseconds.";
      reference
        "RFC 5905 - Network Time Protocol Version 4: Protocol and
         Algorithms Specification";
    }
    leaf root-dispersion {
      type uint64;
      units "milliseconds";
      description
        "Dispersion (epsilon) represents the maximum error inherent
         in the measurement";
      reference
        "RFC 5905 - Network Time Protocol Version 4: Protocol and
         Algorithms Specification";
    }
    leaf offset {
      type uint64;
      units "milliseconds";
      description
        "Estimate of the current time offset from the peer.  This is
         the time difference between the local and reference clock.";
    }
    leaf poll-interval {
      type uint32;
      units "seconds";
      description
        "Polling interval of the peer";
    }
  }

  grouping ncs_rpc_notif_system-ntp-server-top {
    description
      "Top-level grouping for the list of NTP servers";
    container servers {
      description
        "Enclosing container for the list of NTP servers";
      list server {
        key "address";
        description
          "List of NTP servers to use for system clock
           synchronization.  If '/system/ntp/enabled'
           is 'true', then the system will attempt to
           contact and utilize the specified NTP servers.";
        leaf address {
          type leafref {
            path "../config/address";
          }
          description
            "References the configured address or hostname of the
             NTP server.";
        }
        container config {
          description
            "Configuration data for an NTP server.";
          uses ncs_rpc_notif_system-ntp-server-config;
        }
        container state {
          config false;
          description
            "Operational state data for an NTP server.";
          uses ncs_rpc_notif_system-ntp-server-config;
          uses ncs_rpc_notif_system-ntp-server-state;
        }
      }
    }
  }

  grouping ncs_rpc_notif_system-ntp-auth-keys-config {
    description
      "Configuration data ";
    leaf key-id {
      type uint16;
      description
        "Integer identifier used by the client and server to
         designate a secret key.  The client and server must use
         the same key id.";
    }
    leaf key-type {
      type identityref {
        base NTP_AUTH_TYPE;
      }
      description
        "Encryption type used for the NTP authentication key";
    }
    leaf key-value {
      type string;
      description
        "NTP authentication key value";
    }
  }

  grouping ncs_rpc_notif_system-ntp-auth-keys-state {
    description
      "Operational state data for NTP auth key data";
  }

  grouping ncs_rpc_notif_system-ntp-auth-keys-top {
    description
      "Top-level grouping for NTP auth key data";
    container ntp-keys {
      description
        "Enclosing container for list of NTP authentication keys";
      list ntp-key {
        key "key-id";
        description
          "List of NTP authentication keys";
        leaf key-id {
          type leafref {
            path "../config/key-id";
          }
          description
            "Reference to auth key-id list key";
        }
        container config {
          description
            "Configuration data for NTP auth keys";
          uses ncs_rpc_notif_system-ntp-auth-keys-config;
        }
        container state {
          config false;
          description
            "Operational state data for NTP auth keys";
          uses ncs_rpc_notif_system-ntp-auth-keys-config;
          uses ncs_rpc_notif_system-ntp-auth-keys-state;
        }
      }
    }
  }

  grouping ncs_rpc_notif_system-ntp-config {
    description
      "Configuration data for system-wide NTP operation.";
    leaf enabled {
      type boolean;
      default "false";
      description
        "Enables and disables the NTP protocol and indicates that the system should
         attempt to synchronize the system clock with an NTP server
         from the servers defined in the 'ntp/server' list.";
    }
    leaf ntp-source-address {
      type oc-inet:ncs_rpc_notif_ip-address;
      description
        "Source address to use on outgoing NTP packets";
    }
    leaf enable-ntp-auth {
      type boolean;
      default "false";
      description
        "Enable or disable NTP authentication -- when enabled, the
         system will only use packets containing a trusted
         authentication key to synchronize the time.";
    }
  }

  grouping ncs_rpc_notif_system-ntp-state {
    description
      "Operational state data for system-wide NTP operation.";
    leaf auth-mismatch {
      type oc-yang:ncs_rpc_notif_counter64;
      description
        "Count of the number of NTP packets received that were not
         processed due to authentication mismatch.";
    }
  }

  grouping ncs_rpc_notif_system-ntp-top {
    description
      "Top-level grouping for configuration and state data for NTP";
    container ntp {
      description
        "Top-level container for NTP configuration and state";
      container config {
        description
          "Configuration data for NTP client.";
        uses ncs_rpc_notif_system-ntp-config;
      }
      container state {
        config false;
        description
          "Operational state data for NTP services.";
        uses ncs_rpc_notif_system-ntp-config;
        uses ncs_rpc_notif_system-ntp-state;
      }
      uses ncs_rpc_notif_system-ntp-auth-keys-top;
      uses ncs_rpc_notif_system-ntp-server-top;
    }
  }

  grouping ncs_rpc_notif_system-routing-macaddr-config {
    description
      "Configuration data for system's routing MAC addresses.";
    leaf routing-mac {
      type oc-yang:ncs_rpc_notif_mac-address;
      description
        "Any packets destined to this MAC address must be sent through the
         routing pipeline by the system. This MAC address is used to identify
         routed packets in addition to any other MAC addresses that the system
         may already have been using to perform routing.

         It is not expected that this MAC address will be used as the
         source MAC address of any routed packet, as the source MAC address of
         any packets generated by the system, or a MAC address used in ARP
         response. This MAC address may not be allocated from the block of
         MAC address that system owns. For instance, it's allocation could
         be managed by an external controller.";
    }
  }

  grouping ncs_rpc_notif_system-macaddr-top {
    description
      "Top-level grouping for configuration and state of system's MAC addresses.";
    container mac-address {
      description
        "Top-level container for system's MAC address configuration and state";
      container config {
        description
          "Configuration data for routing MAC address.";
        uses ncs_rpc_notif_system-routing-macaddr-config;
      }
      container state {
        config false;
        description
          "Operational state data for routing MAC address.";
        uses ncs_rpc_notif_system-routing-macaddr-config;
      }
    }
  }

  grouping ncs_rpc_notif_system-memory-config {
    description
      "Configuration data for system memory";
  }

  grouping ncs_rpc_notif_system-memory-state {
    description
      "Operational state data for system memory";
    leaf physical {
      type uint64;
      units "bytes";
      description
        "Reports the total physical memory available on the
         system.";
    }
    leaf reserved {
      type uint64;
      units "bytes";
      description
        "Memory reserved for system use";
    }
    leaf used {
      type uint64;
      units "bytes";
      description
        "Memory that has been used and not available for allocation.";
    }
    leaf free {
      type uint64;
      units "bytes";
      description
        "Memory that is not used and is available for allocation.";
    }
  }

  grouping ncs_rpc_notif_system-memory-error-counters {
    description
      "Counters for system memory errors.";
    leaf correctable-ecc-errors {
      type uint64;
      description
        "Count of correctable ECC errors. Systems with ECC memory
         are capable of correcting Single-bit ECC errors.";
    }
    leaf uncorrectable-ecc-errors {
      type uint64;
      description
        "Count of uncorrectable ECC errors. Systems with ECC
         memory are capable of detecting multi-bit ECC errors,
         but cannot correct them.";
    }
    leaf total-ecc-errors {
      type uint64;
      description
        "Count of total ECC errors, this includes both correctable
         and uncorrectable ECC errors.";
    }
  }

  grouping ncs_rpc_notif_system-memory-top {
    description
      "Top-level grouping for system memory data definitions";
    container memory {
      description
        "Top-level container for system memory data";
      container config {
        description
          "Configuration data for system memory";
        uses ncs_rpc_notif_system-memory-config;
      }
      container state {
        config false;
        description
          "Operational state data for system memory";
        container counters {
          description
            "Counters for tracking system memory errors";
          uses ncs_rpc_notif_system-memory-error-counters;
        }
        uses ncs_rpc_notif_system-memory-config;
        uses ncs_rpc_notif_system-memory-state;
      }
    }
  }

  grouping ncs_rpc_notif_system-cpu-state {
    description
      "Operational state data for the system CPU(s)";
    leaf index {
      type union {
        type enumeration {
          enum "ALL" {
            description
              "Index value indicating all CPUs in the system";
          }
        }
        type uint32;
      }
      description
        "The CPU index for each processor core on the system.  On a
         single-core system, the index should be zero.  The ALL
         index signifies an aggregation of the CPU utilization
         statistics over all cores in the system.";
    }
    container total {
      description
        "Total CPU utilization.";
      uses oc-types:ncs_rpc_notif_avg-min-max-instant-stats-pct;
    }
    container user {
      description
        "Percentage of CPU time spent running in user space.";
      uses oc-types:ncs_rpc_notif_avg-min-max-instant-stats-pct;
    }
    container kernel {
      description
        "Percentage of CPU time spent running in kernel space.";
      uses oc-types:ncs_rpc_notif_avg-min-max-instant-stats-pct;
    }
    container nice {
      description
        "Percentage of CPU time spent running low-priority (niced)
         user processes.";
      uses oc-types:ncs_rpc_notif_avg-min-max-instant-stats-pct;
    }
    container idle {
      description
        "Percentage of CPU time spent idle.";
      uses oc-types:ncs_rpc_notif_avg-min-max-instant-stats-pct;
    }
    container wait {
      description
        "Percentage of CPU time spent waiting for I/O.";
      uses oc-types:ncs_rpc_notif_avg-min-max-instant-stats-pct;
    }
    container hardware-interrupt {
      description
        "Percentage of CPU time spent servicing hardware interrupts.";
      uses oc-types:ncs_rpc_notif_avg-min-max-instant-stats-pct;
    }
    container software-interrupt {
      description
        "Percentage of CPU time spent servicing software interrupts";
      uses oc-types:ncs_rpc_notif_avg-min-max-instant-stats-pct;
    }
  }

  grouping ncs_rpc_notif_system-cpu-top {
    description
      "Top-level grouping for system CPU data";
    container cpus {
      config false;
      description
        "Enclosing container for the list of CPU cores on the
         system";
      list cpu {
        key "index";
        description
          "List of CPU cores on the system (including logical CPUs
           on hyperthreaded systems), keyed by either a numerical
           index, or the ALL value for an entry representing the
           aggregation across all CPUs.";
        leaf index {
          type leafref {
            path "../state/index";
          }
          description
            "Reference to list key";
        }
        container state {
          description
            "Operational state data for the system CPU(s)";
          uses ncs_rpc_notif_system-cpu-state;
        }
      }
    }
  }

  grouping ncs_rpc_notif_system-top {
    description
      "Top level system data containers";
    container system {
      description
        "Enclosing container for system-related configuration and
         operational state data";
      container config {
        description
          "Global configuration data for the system";
        uses ncs_rpc_notif_system-global-config;
      }
      container state {
        config false;
        description
          "Global operational state data for the system";
        uses ncs_rpc_notif_system-global-config;
        uses ncs_rpc_notif_system-global-state;
      }
      uses ncs_rpc_notif_mount-points-top;
      uses ncs_rpc_notif_system-clock-top;
      uses ncs_rpc_notif_system-dns-top;
      uses ncs_rpc_notif_system-ntp-top;
      uses oc-sys-term:ncs_rpc_notif_system-ssh-server-top;
      uses oc-sys-term:ncs_rpc_notif_system-telnet-server-top;
      uses oc-log:ncs_rpc_notif_logging-top;
      uses oc-aaa:ncs_rpc_notif_aaa-top;
      uses ncs_rpc_notif_system-memory-top;
      uses ncs_rpc_notif_system-cpu-top;
      uses oc-proc:ncs_rpc_notif_procmon-processes-top;
      uses oc-alarms:ncs_rpc_notif_alarms-top;
      uses oc-messages:ncs_rpc_notif_messages-top;
      uses oc-license:ncs_rpc_notif_license-top;
      uses ncs_rpc_notif_system-macaddr-top;
    }
  }

  grouping live_ncs_system-clock-config {
    description
      "Configuration data for system-wide clock configuration";
    leaf timezone-name {
      type live_ncs_timezone-name-type;
      description
        "The TZ database name to use for the system, such
         as 'Europe/Stockholm'.";
      reference
        "IANA Time Zone Database
         http://www.iana.org/time-zones";
    }
  }

  grouping live_ncs_system-clock-state {
    description
      "Operational state data for system-wide clock configuration";
  }

  grouping live_ncs_system-clock-top {
    description
      "Top-level grouping for system-wide clock configuration";
    container clock {
      description
        "Top-level container for clock configuration data";
      container config {
        description
          "Configuration data for system clock";
        uses live_ncs_system-clock-config;
      }
      container state {
        description
          "Operational state data for system clock";
        uses live_ncs_system-clock-config;
        uses live_ncs_system-clock-state;
      }
    }
  }

  grouping live_ncs_system-global-config {
    description
      "system-wide configuration parameters";
    leaf hostname {
      type oc-inet:live_ncs_domain-name;
      description
        "The hostname of the device -- should be a single domain
         label, without the domain.";
    }
    leaf domain-name {
      type oc-inet:live_ncs_domain-name;
      description
        "Specifies the domain name used to form fully qualified name
         for unqualified hostnames.";
    }
    leaf login-banner {
      type string;
      description
        "The console login message displayed before the login prompt,
         i.e., before a user logs into the system.";
    }
    leaf motd-banner {
      type string;
      description
        "The console message displayed after a user logs into the
         system.  They system may append additional standard
         information such as the current system date and time, uptime,
         last login timestamp, etc.";
    }
  }

  grouping live_ncs_mount-point-state {
    description
      "Operational state data for the mount point.";
    leaf name {
      type string;
      description
        "Mount point name.";
    }
    leaf storage-component {
      type leafref {
        path "/ncs:devices/ncs:device/ncs:live-status/oc-platform:components/oc-platform:component/oc-platform:name" {
          tailf:xpath-root 3;
        }
      }
      description
        "In the case that the filesystem that is mounted corresponds to a
         physical or logical component within the system, this leaf provides
         a reference to the hosting component within the /components
         hierarchy.

         The reference should be to the most specific component (e.g., if an
         entry for /dev/sda1 exists, then this should be referred to,
         otherwise a reference to /dev/sda may be provided.";
    }
    leaf size {
      type uint64;
      units "megabytes";
      description
        "The total size of the initialised filesystem.";
    }
    leaf available {
      type uint64;
      units "megabytes";
      description
        "The amount of unused space on the filesystem.";
    }
    leaf utilized {
      type uint64;
      units "megabytes";
      description
        "The amount of space currently in use on the filesystem.";
    }
  }

  grouping live_ncs_system-global-state {
    description
      "Global operational state data for the system";
    leaf current-datetime {
      type oc-yang:live_ncs_date-and-time;
      description
        "The current system date and time.";
    }
    leaf boot-time {
      type oc-types:live_ncs_timeticks64;
      units "nanoseconds";
      description
        "This timestamp indicates the time that the system was last
         restarted.  The value is the timestamp in nanoseconds relative
         to the Unix Epoch (Jan 1, 1970 00:00:00 UTC).";
    }
    leaf software-version {
      type string;
      description
        "Operating system version of the currently active controller
         of the device.  It is required that this value matches the
         value of the state/software-version leaf in the component
         of type OPERATING_SYSTEM.";
    }
    leaf last-configuration-timestamp {
      type oc-types:live_ncs_timeticks64;
      units "nanoseconds";
      description
        "Indicates the monotonically increasing timestamp at which the
         last configuration change was made. This may may be through CLI,
         gNMI or some other mechanism.";
    }
  }

  grouping live_ncs_mount-points-top {
    description
      "Top-level grouping for mount points data.";
    container mount-points {
      description
        "When a system has a set of filesystems that are attached to a
         directory (i.e., mounted on the system) they are expected to be
         present in this list. If the system has the concept of mounting
         physical or virtual resources to a mount point within the root
         filesystem (/) they should also be included in this list.";
      list mount-point {
        key "name";
        description
          "List of mount points in the system.";
        leaf name {
          type leafref {
            path "../state/name";
          }
          description
            "Reference to the key for list of mount points.";
        }
        container state {
          description
            "State of system mount point.";
          uses live_ncs_mount-point-state;
        }
      }
    }
  }

  grouping live_ncs_system-dns-config {
    description
      "DNS / resolver related configuration data";
    leaf-list search {
      type oc-inet:live_ncs_domain-name;
      ordered-by user;
      description
        "An ordered list of domains to search when resolving
         a host name.";
    }
  }

  grouping live_ncs_system-dns-state {
    description
      "Operational state data for system DNS resolver";
  }

  grouping live_ncs_system-dns-servers-config {
    description
      "Configuration data for DNS resolvers";
    leaf address {
      type oc-inet:live_ncs_ip-address;
      description
        "The address of the DNS server, can be either IPv4
         or IPv6.";
    }
    leaf port {
      type oc-inet:live_ncs_port-number;
      // NCS drop default statement
      description
        "The port number of the DNS server.";
    }
  }

  grouping live_ncs_system-dns-static-config {
    description
      "Configuration data for static host entries";
    leaf hostname {
      type string;
      description
        "Hostname for the static DNS entry";
    }
    leaf-list alias {
      type string;
      description
        "Additional aliases for the hostname";
    }
    leaf-list ipv4-address {
      type oc-inet:live_ncs_ipv4-address;
      description
        "List of IPv4 addresses for the host entry";
    }
    leaf-list ipv6-address {
      type oc-inet:live_ncs_ipv6-address;
      description
        "List of IPv6 addresses for the host entry";
    }
  }

  grouping live_ncs_system-dns-static-state {
    description
      "Operational state data for static host entries";
  }

  grouping live_ncs_system-dns-static-top {
    description
      "Top-level grouping for static DNS host entries";
    container host-entries {
      description
        "Enclosing container for list of static host entries";
      list host-entry {
        key "hostname";
        description
          "List of static host entries";
        leaf hostname {
          type leafref {
            path "../config/hostname";
          }
          description
            "Reference to the hostname list key";
        }
        container config {
          description
            "Configuration data for static host entries";
          uses live_ncs_system-dns-static-config;
        }
        container state {
          description
            "Operational state data for static host entries";
          uses live_ncs_system-dns-static-config;
          uses live_ncs_system-dns-static-state;
        }
      }
    }
  }

  grouping live_ncs_system-dns-servers-state {
    description
      "Operational state data for DNS resolvers";
  }

  grouping live_ncs_system-dns-servers-top {
    description
      "Top-level grouping for the list of DNS resolvers.";
    container servers {
      description
        "Enclosing container for DNS resolver list";
      list server {
        key "address";
        ordered-by user;
        description
          "List of the DNS servers that the resolver should query.

           When the resolver is invoked by a calling application, it
           sends the query to the first name server in this list.  If
           no response has been received within 'timeout' seconds,
           the resolver continues with the next server in the list.
           If no response is received from any server, the resolver
           continues with the first server again.  When the resolver
           has traversed the list 'attempts' times without receiving
           any response, it gives up and returns an error to the
           calling application.

           Implementations MAY limit the number of entries in this
           list.";
        leaf address {
          type leafref {
            path "../config/address";
          }
          description
            "References the configured address of the DNS server";
        }
        container config {
          description
            "Configuration data for each DNS resolver";
          uses live_ncs_system-dns-servers-config;
        }
        container state {
          description
            "Operational state data for each DNS resolver";
          uses live_ncs_system-dns-servers-config;
          uses live_ncs_system-dns-servers-state;
        }
      }
    }
  }

  grouping live_ncs_system-dns-top {
    description
      "Top-level grouping for DNS / resolver config and operational
       state data";
    container dns {
      description
        "Enclosing container for DNS resolver data";
      container config {
        description
          "Configuration data for the DNS resolver";
        uses live_ncs_system-dns-config;
      }
      container state {
        description
          "Operational state data for the DNS resolver";
        uses live_ncs_system-dns-config;
        uses live_ncs_system-dns-state;
      }
      uses live_ncs_system-dns-servers-top;
      uses live_ncs_system-dns-static-top;
    }
  }

  grouping live_ncs_system-ntp-server-config {
    description
      "Configuration data for NTP servers";
    leaf address {
      type oc-inet:live_ncs_host;
      description
        "The address or hostname of the NTP server.";
    }
    leaf port {
      type oc-inet:live_ncs_port-number;
      // NCS drop default statement
      description
        "The port number of the NTP server.";
    }
    leaf version {
      type uint8 {
        range "1..4";
      }
      // NCS drop default statement
      description
        "Version number to put in outgoing NTP packets";
    }
    leaf association-type {
      type enumeration {
        enum "SERVER" {
          description
            "Use client association mode.  This device
             will not provide synchronization to the
             configured NTP server.";
        }
        enum "PEER" {
          description
            "Use symmetric active association mode.
             This device may provide synchronization
             to the configured NTP server.";
        }
        enum "POOL" {
          description
            "Use client association mode with one or
             more of the NTP servers found by DNS
             resolution of the domain name given by
             the 'address' leaf.  This device will not
             provide synchronization to the servers.";
        }
      }
      // NCS drop default statement
      description
        "The desired association type for this NTP server.";
    }
    leaf iburst {
      type boolean;
      // NCS drop default statement
      description
        "Indicates whether this server should enable burst
         synchronization or not.";
    }
    leaf prefer {
      type boolean;
      // NCS drop default statement
      description
        "Indicates whether this server should be preferred
         or not.";
    }
  }

  grouping live_ncs_system-ntp-server-state {
    description
      "Operational state data for NTP servers";
    leaf stratum {
      type uint8;
      description
        "Indicates the level of the server in the NTP hierarchy. As
         stratum number increases, the accuracy is degraded.  Primary
         servers are stratum while a maximum value of 16 indicates
         unsynchronized.  The values have the following specific
         semantics:

         | 0      | unspecified or invalid
         | 1      | primary server (e.g., equipped with a GPS receiver)
         | 2-15   | secondary server (via NTP)
         | 16     | unsynchronized
         | 17-255 | reserved";
      reference
        "RFC 5905 - Network Time Protocol Version 4: Protocol and
         Algorithms Specification";
    }
    leaf root-delay {
      type uint32;
      units "milliseconds";
      description
        "The round-trip delay to the server, in milliseconds.";
      reference
        "RFC 5905 - Network Time Protocol Version 4: Protocol and
         Algorithms Specification";
    }
    leaf root-dispersion {
      type uint64;
      units "milliseconds";
      description
        "Dispersion (epsilon) represents the maximum error inherent
         in the measurement";
      reference
        "RFC 5905 - Network Time Protocol Version 4: Protocol and
         Algorithms Specification";
    }
    leaf offset {
      type uint64;
      units "milliseconds";
      description
        "Estimate of the current time offset from the peer.  This is
         the time difference between the local and reference clock.";
    }
    leaf poll-interval {
      type uint32;
      units "seconds";
      description
        "Polling interval of the peer";
    }
  }

  grouping live_ncs_system-ntp-server-top {
    description
      "Top-level grouping for the list of NTP servers";
    container servers {
      description
        "Enclosing container for the list of NTP servers";
      list server {
        key "address";
        description
          "List of NTP servers to use for system clock
           synchronization.  If '/system/ntp/enabled'
           is 'true', then the system will attempt to
           contact and utilize the specified NTP servers.";
        leaf address {
          type leafref {
            path "../config/address";
          }
          description
            "References the configured address or hostname of the
             NTP server.";
        }
        container config {
          description
            "Configuration data for an NTP server.";
          uses live_ncs_system-ntp-server-config;
        }
        container state {
          description
            "Operational state data for an NTP server.";
          uses live_ncs_system-ntp-server-config;
          uses live_ncs_system-ntp-server-state;
        }
      }
    }
  }

  grouping live_ncs_system-ntp-auth-keys-config {
    description
      "Configuration data ";
    leaf key-id {
      type uint16;
      description
        "Integer identifier used by the client and server to
         designate a secret key.  The client and server must use
         the same key id.";
    }
    leaf key-type {
      type identityref {
        base NTP_AUTH_TYPE;
      }
      description
        "Encryption type used for the NTP authentication key";
    }
    leaf key-value {
      type string;
      description
        "NTP authentication key value";
    }
  }

  grouping live_ncs_system-ntp-auth-keys-state {
    description
      "Operational state data for NTP auth key data";
  }

  grouping live_ncs_system-ntp-auth-keys-top {
    description
      "Top-level grouping for NTP auth key data";
    container ntp-keys {
      description
        "Enclosing container for list of NTP authentication keys";
      list ntp-key {
        key "key-id";
        description
          "List of NTP authentication keys";
        leaf key-id {
          type leafref {
            path "../config/key-id";
          }
          description
            "Reference to auth key-id list key";
        }
        container config {
          description
            "Configuration data for NTP auth keys";
          uses live_ncs_system-ntp-auth-keys-config;
        }
        container state {
          description
            "Operational state data for NTP auth keys";
          uses live_ncs_system-ntp-auth-keys-config;
          uses live_ncs_system-ntp-auth-keys-state;
        }
      }
    }
  }

  grouping live_ncs_system-ntp-config {
    description
      "Configuration data for system-wide NTP operation.";
    leaf enabled {
      type boolean;
      // NCS drop default statement
      description
        "Enables and disables the NTP protocol and indicates that the system should
         attempt to synchronize the system clock with an NTP server
         from the servers defined in the 'ntp/server' list.";
    }
    leaf ntp-source-address {
      type oc-inet:live_ncs_ip-address;
      description
        "Source address to use on outgoing NTP packets";
    }
    leaf enable-ntp-auth {
      type boolean;
      // NCS drop default statement
      description
        "Enable or disable NTP authentication -- when enabled, the
         system will only use packets containing a trusted
         authentication key to synchronize the time.";
    }
  }

  grouping live_ncs_system-ntp-state {
    description
      "Operational state data for system-wide NTP operation.";
    leaf auth-mismatch {
      type oc-yang:live_ncs_counter64;
      description
        "Count of the number of NTP packets received that were not
         processed due to authentication mismatch.";
    }
  }

  grouping live_ncs_system-ntp-top {
    description
      "Top-level grouping for configuration and state data for NTP";
    container ntp {
      description
        "Top-level container for NTP configuration and state";
      container config {
        description
          "Configuration data for NTP client.";
        uses live_ncs_system-ntp-config;
      }
      container state {
        description
          "Operational state data for NTP services.";
        uses live_ncs_system-ntp-config;
        uses live_ncs_system-ntp-state;
      }
      uses live_ncs_system-ntp-auth-keys-top;
      uses live_ncs_system-ntp-server-top;
    }
  }

  grouping live_ncs_system-routing-macaddr-config {
    description
      "Configuration data for system's routing MAC addresses.";
    leaf routing-mac {
      type oc-yang:live_ncs_mac-address;
      description
        "Any packets destined to this MAC address must be sent through the
         routing pipeline by the system. This MAC address is used to identify
         routed packets in addition to any other MAC addresses that the system
         may already have been using to perform routing.

         It is not expected that this MAC address will be used as the
         source MAC address of any routed packet, as the source MAC address of
         any packets generated by the system, or a MAC address used in ARP
         response. This MAC address may not be allocated from the block of
         MAC address that system owns. For instance, it's allocation could
         be managed by an external controller.";
    }
  }

  grouping live_ncs_system-macaddr-top {
    description
      "Top-level grouping for configuration and state of system's MAC addresses.";
    container mac-address {
      description
        "Top-level container for system's MAC address configuration and state";
      container config {
        description
          "Configuration data for routing MAC address.";
        uses live_ncs_system-routing-macaddr-config;
      }
      container state {
        description
          "Operational state data for routing MAC address.";
        uses live_ncs_system-routing-macaddr-config;
      }
    }
  }

  grouping live_ncs_system-memory-config {
    description
      "Configuration data for system memory";
  }

  grouping live_ncs_system-memory-state {
    description
      "Operational state data for system memory";
    leaf physical {
      type uint64;
      units "bytes";
      description
        "Reports the total physical memory available on the
         system.";
    }
    leaf reserved {
      type uint64;
      units "bytes";
      description
        "Memory reserved for system use";
    }
    leaf used {
      type uint64;
      units "bytes";
      description
        "Memory that has been used and not available for allocation.";
    }
    leaf free {
      type uint64;
      units "bytes";
      description
        "Memory that is not used and is available for allocation.";
    }
  }

  grouping live_ncs_system-memory-error-counters {
    description
      "Counters for system memory errors.";
    leaf correctable-ecc-errors {
      type uint64;
      description
        "Count of correctable ECC errors. Systems with ECC memory
         are capable of correcting Single-bit ECC errors.";
    }
    leaf uncorrectable-ecc-errors {
      type uint64;
      description
        "Count of uncorrectable ECC errors. Systems with ECC
         memory are capable of detecting multi-bit ECC errors,
         but cannot correct them.";
    }
    leaf total-ecc-errors {
      type uint64;
      description
        "Count of total ECC errors, this includes both correctable
         and uncorrectable ECC errors.";
    }
  }

  grouping live_ncs_system-memory-top {
    description
      "Top-level grouping for system memory data definitions";
    container memory {
      description
        "Top-level container for system memory data";
      container config {
        description
          "Configuration data for system memory";
        uses live_ncs_system-memory-config;
      }
      container state {
        description
          "Operational state data for system memory";
        container counters {
          description
            "Counters for tracking system memory errors";
          uses live_ncs_system-memory-error-counters;
        }
        uses live_ncs_system-memory-config;
        uses live_ncs_system-memory-state;
      }
    }
  }

  grouping live_ncs_system-cpu-state {
    description
      "Operational state data for the system CPU(s)";
    leaf index {
      type union {
        type enumeration {
          enum "ALL" {
            description
              "Index value indicating all CPUs in the system";
          }
        }
        type uint32;
      }
      description
        "The CPU index for each processor core on the system.  On a
         single-core system, the index should be zero.  The ALL
         index signifies an aggregation of the CPU utilization
         statistics over all cores in the system.";
    }
    container total {
      description
        "Total CPU utilization.";
      uses oc-types:live_ncs_avg-min-max-instant-stats-pct;
    }
    container user {
      description
        "Percentage of CPU time spent running in user space.";
      uses oc-types:live_ncs_avg-min-max-instant-stats-pct;
    }
    container kernel {
      description
        "Percentage of CPU time spent running in kernel space.";
      uses oc-types:live_ncs_avg-min-max-instant-stats-pct;
    }
    container nice {
      description
        "Percentage of CPU time spent running low-priority (niced)
         user processes.";
      uses oc-types:live_ncs_avg-min-max-instant-stats-pct;
    }
    container idle {
      description
        "Percentage of CPU time spent idle.";
      uses oc-types:live_ncs_avg-min-max-instant-stats-pct;
    }
    container wait {
      description
        "Percentage of CPU time spent waiting for I/O.";
      uses oc-types:live_ncs_avg-min-max-instant-stats-pct;
    }
    container hardware-interrupt {
      description
        "Percentage of CPU time spent servicing hardware interrupts.";
      uses oc-types:live_ncs_avg-min-max-instant-stats-pct;
    }
    container software-interrupt {
      description
        "Percentage of CPU time spent servicing software interrupts";
      uses oc-types:live_ncs_avg-min-max-instant-stats-pct;
    }
  }

  grouping live_ncs_system-cpu-top {
    description
      "Top-level grouping for system CPU data";
    container cpus {
      description
        "Enclosing container for the list of CPU cores on the
         system";
      list cpu {
        key "index";
        description
          "List of CPU cores on the system (including logical CPUs
           on hyperthreaded systems), keyed by either a numerical
           index, or the ALL value for an entry representing the
           aggregation across all CPUs.";
        leaf index {
          type leafref {
            path "../state/index";
          }
          description
            "Reference to list key";
        }
        container state {
          description
            "Operational state data for the system CPU(s)";
          uses live_ncs_system-cpu-state;
        }
      }
    }
  }

  grouping live_ncs_system-top {
    description
      "Top level system data containers";
    container system {
      description
        "Enclosing container for system-related configuration and
         operational state data";
      container config {
        description
          "Global configuration data for the system";
        uses live_ncs_system-global-config;
      }
      container state {
        description
          "Global operational state data for the system";
        uses live_ncs_system-global-config;
        uses live_ncs_system-global-state;
      }
      uses live_ncs_mount-points-top;
      uses live_ncs_system-clock-top;
      uses live_ncs_system-dns-top;
      uses live_ncs_system-ntp-top;
      uses oc-sys-term:live_ncs_system-ssh-server-top;
      uses oc-sys-term:live_ncs_system-telnet-server-top;
      uses oc-log:live_ncs_logging-top;
      uses oc-aaa:live_ncs_aaa-top;
      uses live_ncs_system-memory-top;
      uses live_ncs_system-cpu-top;
      uses oc-proc:live_ncs_procmon-processes-top;
      uses oc-alarms:live_ncs_alarms-top;
      uses oc-messages:live_ncs_messages-top;
      uses oc-license:live_ncs_license-top;
      uses live_ncs_system-macaddr-top;
    }
  }

  grouping system-clock-config {
    description
      "Configuration data for system-wide clock configuration";
    leaf timezone-name {
      type timezone-name-type;
      description
        "The TZ database name to use for the system, such
         as 'Europe/Stockholm'.";
      reference
        "IANA Time Zone Database
         http://www.iana.org/time-zones";
    }
  }

  grouping system-clock-state {
    description
      "Operational state data for system-wide clock configuration";
  }

  grouping system-clock-top {
    description
      "Top-level grouping for system-wide clock configuration";
    container clock {
      description
        "Top-level container for clock configuration data";
      container config {
        description
          "Configuration data for system clock";
        uses system-clock-config;
      }
      // NCS drop config false container state
    }
  }

  grouping system-global-config {
    description
      "system-wide configuration parameters";
    leaf hostname {
      type oc-inet:domain-name;
      description
        "The hostname of the device -- should be a single domain
         label, without the domain.";
    }
    leaf domain-name {
      type oc-inet:domain-name;
      description
        "Specifies the domain name used to form fully qualified name
         for unqualified hostnames.";
    }
    leaf login-banner {
      type string;
      description
        "The console login message displayed before the login prompt,
         i.e., before a user logs into the system.";
    }
    leaf motd-banner {
      type string;
      description
        "The console message displayed after a user logs into the
         system.  They system may append additional standard
         information such as the current system date and time, uptime,
         last login timestamp, etc.";
    }
  }

  grouping mount-point-state {
    description
      "Operational state data for the mount point.";
    leaf name {
      type string;
      description
        "Mount point name.";
    }
    leaf storage-component {
      type leafref {
        path "/ncs:devices/ncs:device/ncs:config/oc-platform:components/oc-platform:component/oc-platform:name" {
          tailf:xpath-root 3;
        }
      }
      description
        "In the case that the filesystem that is mounted corresponds to a
         physical or logical component within the system, this leaf provides
         a reference to the hosting component within the /components
         hierarchy.

         The reference should be to the most specific component (e.g., if an
         entry for /dev/sda1 exists, then this should be referred to,
         otherwise a reference to /dev/sda may be provided.";
    }
    leaf size {
      type uint64;
      units "megabytes";
      description
        "The total size of the initialised filesystem.";
    }
    leaf available {
      type uint64;
      units "megabytes";
      description
        "The amount of unused space on the filesystem.";
    }
    leaf utilized {
      type uint64;
      units "megabytes";
      description
        "The amount of space currently in use on the filesystem.";
    }
  }

  grouping system-global-state {
    description
      "Global operational state data for the system";
    leaf current-datetime {
      type oc-yang:date-and-time;
      description
        "The current system date and time.";
    }
    leaf boot-time {
      type oc-types:timeticks64;
      units "nanoseconds";
      description
        "This timestamp indicates the time that the system was last
         restarted.  The value is the timestamp in nanoseconds relative
         to the Unix Epoch (Jan 1, 1970 00:00:00 UTC).";
    }
    leaf software-version {
      type string;
      description
        "Operating system version of the currently active controller
         of the device.  It is required that this value matches the
         value of the state/software-version leaf in the component
         of type OPERATING_SYSTEM.";
    }
    leaf last-configuration-timestamp {
      type oc-types:timeticks64;
      units "nanoseconds";
      description
        "Indicates the monotonically increasing timestamp at which the
         last configuration change was made. This may may be through CLI,
         gNMI or some other mechanism.";
    }
  }

  grouping mount-points-top {
    description
      "Top-level grouping for mount points data.";
    // NCS drop config false container 'mount-points'
  }

  grouping system-dns-config {
    description
      "DNS / resolver related configuration data";
    leaf-list search {
      type oc-inet:domain-name;
      ordered-by user;
      description
        "An ordered list of domains to search when resolving
         a host name.";
    }
  }

  grouping system-dns-state {
    description
      "Operational state data for system DNS resolver";
  }

  grouping system-dns-servers-config {
    description
      "Configuration data for DNS resolvers";
    leaf address {
      type oc-inet:ip-address;
      description
        "The address of the DNS server, can be either IPv4
         or IPv6.";
    }
    leaf port {
      type oc-inet:port-number;
      default "53";
      description
        "The port number of the DNS server.";
    }
  }

  grouping system-dns-static-config {
    description
      "Configuration data for static host entries";
    leaf hostname {
      type string;
      description
        "Hostname for the static DNS entry";
    }
    leaf-list alias {
      type string;
      description
        "Additional aliases for the hostname";
    }
    leaf-list ipv4-address {
      type oc-inet:ipv4-address;
      description
        "List of IPv4 addresses for the host entry";
    }
    leaf-list ipv6-address {
      type oc-inet:ipv6-address;
      description
        "List of IPv6 addresses for the host entry";
    }
  }

  grouping system-dns-static-state {
    description
      "Operational state data for static host entries";
  }

  grouping system-dns-static-top {
    description
      "Top-level grouping for static DNS host entries";
    container host-entries {
      description
        "Enclosing container for list of static host entries";
      list host-entry {
        key "hostname";
        description
          "List of static host entries";
        leaf hostname {
          type leafref {
            path "../config/hostname";
          }
          description
            "Reference to the hostname list key";
        }
        container config {
          description
            "Configuration data for static host entries";
          uses system-dns-static-config;
        }
        // NCS drop config false container state
      }
    }
  }

  grouping system-dns-servers-state {
    description
      "Operational state data for DNS resolvers";
  }

  grouping system-dns-servers-top {
    description
      "Top-level grouping for the list of DNS resolvers.";
    container servers {
      description
        "Enclosing container for DNS resolver list";
      list server {
        key "address";
        ordered-by user;
        description
          "List of the DNS servers that the resolver should query.

           When the resolver is invoked by a calling application, it
           sends the query to the first name server in this list.  If
           no response has been received within 'timeout' seconds,
           the resolver continues with the next server in the list.
           If no response is received from any server, the resolver
           continues with the first server again.  When the resolver
           has traversed the list 'attempts' times without receiving
           any response, it gives up and returns an error to the
           calling application.

           Implementations MAY limit the number of entries in this
           list.";
        leaf address {
          type leafref {
            path "../config/address";
          }
          description
            "References the configured address of the DNS server";
        }
        container config {
          description
            "Configuration data for each DNS resolver";
          uses system-dns-servers-config;
        }
        // NCS drop config false container state
      }
    }
  }

  grouping system-dns-top {
    description
      "Top-level grouping for DNS / resolver config and operational
       state data";
    container dns {
      description
        "Enclosing container for DNS resolver data";
      container config {
        description
          "Configuration data for the DNS resolver";
        uses system-dns-config;
      }
      // NCS drop config false container state
      uses system-dns-servers-top;
      uses system-dns-static-top;
    }
  }

  grouping system-ntp-server-config {
    description
      "Configuration data for NTP servers";
    leaf address {
      type oc-inet:host;
      description
        "The address or hostname of the NTP server.";
    }
    leaf port {
      type oc-inet:port-number;
      default "123";
      description
        "The port number of the NTP server.";
    }
    leaf version {
      type uint8 {
        range "1..4";
      }
      default "4";
      description
        "Version number to put in outgoing NTP packets";
    }
    leaf association-type {
      type enumeration {
        enum "SERVER" {
          description
            "Use client association mode.  This device
             will not provide synchronization to the
             configured NTP server.";
        }
        enum "PEER" {
          description
            "Use symmetric active association mode.
             This device may provide synchronization
             to the configured NTP server.";
        }
        enum "POOL" {
          description
            "Use client association mode with one or
             more of the NTP servers found by DNS
             resolution of the domain name given by
             the 'address' leaf.  This device will not
             provide synchronization to the servers.";
        }
      }
      default "SERVER";
      description
        "The desired association type for this NTP server.";
    }
    leaf iburst {
      type boolean;
      default "false";
      description
        "Indicates whether this server should enable burst
         synchronization or not.";
    }
    leaf prefer {
      type boolean;
      default "false";
      description
        "Indicates whether this server should be preferred
         or not.";
    }
  }

  grouping system-ntp-server-state {
    description
      "Operational state data for NTP servers";
    leaf stratum {
      type uint8;
      description
        "Indicates the level of the server in the NTP hierarchy. As
         stratum number increases, the accuracy is degraded.  Primary
         servers are stratum while a maximum value of 16 indicates
         unsynchronized.  The values have the following specific
         semantics:

         | 0      | unspecified or invalid
         | 1      | primary server (e.g., equipped with a GPS receiver)
         | 2-15   | secondary server (via NTP)
         | 16     | unsynchronized
         | 17-255 | reserved";
      reference
        "RFC 5905 - Network Time Protocol Version 4: Protocol and
         Algorithms Specification";
    }
    leaf root-delay {
      type uint32;
      units "milliseconds";
      description
        "The round-trip delay to the server, in milliseconds.";
      reference
        "RFC 5905 - Network Time Protocol Version 4: Protocol and
         Algorithms Specification";
    }
    leaf root-dispersion {
      type uint64;
      units "milliseconds";
      description
        "Dispersion (epsilon) represents the maximum error inherent
         in the measurement";
      reference
        "RFC 5905 - Network Time Protocol Version 4: Protocol and
         Algorithms Specification";
    }
    leaf offset {
      type uint64;
      units "milliseconds";
      description
        "Estimate of the current time offset from the peer.  This is
         the time difference between the local and reference clock.";
    }
    leaf poll-interval {
      type uint32;
      units "seconds";
      description
        "Polling interval of the peer";
    }
  }

  grouping system-ntp-server-top {
    description
      "Top-level grouping for the list of NTP servers";
    container servers {
      description
        "Enclosing container for the list of NTP servers";
      list server {
        key "address";
        description
          "List of NTP servers to use for system clock
           synchronization.  If '/system/ntp/enabled'
           is 'true', then the system will attempt to
           contact and utilize the specified NTP servers.";
        leaf address {
          type leafref {
            path "../config/address";
          }
          description
            "References the configured address or hostname of the
             NTP server.";
        }
        container config {
          description
            "Configuration data for an NTP server.";
          uses system-ntp-server-config;
        }
        // NCS drop config false container state
      }
    }
  }

  grouping system-ntp-auth-keys-config {
    description
      "Configuration data ";
    leaf key-id {
      type uint16;
      description
        "Integer identifier used by the client and server to
         designate a secret key.  The client and server must use
         the same key id.";
    }
    leaf key-type {
      type identityref {
        base NTP_AUTH_TYPE;
      }
      description
        "Encryption type used for the NTP authentication key";
    }
    leaf key-value {
      type string;
      description
        "NTP authentication key value";
    }
  }

  grouping system-ntp-auth-keys-state {
    description
      "Operational state data for NTP auth key data";
  }

  grouping system-ntp-auth-keys-top {
    description
      "Top-level grouping for NTP auth key data";
    container ntp-keys {
      description
        "Enclosing container for list of NTP authentication keys";
      list ntp-key {
        key "key-id";
        description
          "List of NTP authentication keys";
        leaf key-id {
          type leafref {
            path "../config/key-id";
          }
          description
            "Reference to auth key-id list key";
        }
        container config {
          description
            "Configuration data for NTP auth keys";
          uses system-ntp-auth-keys-config;
        }
        // NCS drop config false container state
      }
    }
  }

  grouping system-ntp-config {
    description
      "Configuration data for system-wide NTP operation.";
    leaf enabled {
      type boolean;
      default "false";
      description
        "Enables and disables the NTP protocol and indicates that the system should
         attempt to synchronize the system clock with an NTP server
         from the servers defined in the 'ntp/server' list.";
    }
    leaf ntp-source-address {
      type oc-inet:ip-address;
      description
        "Source address to use on outgoing NTP packets";
    }
    leaf enable-ntp-auth {
      type boolean;
      default "false";
      description
        "Enable or disable NTP authentication -- when enabled, the
         system will only use packets containing a trusted
         authentication key to synchronize the time.";
    }
  }

  grouping system-ntp-state {
    description
      "Operational state data for system-wide NTP operation.";
    leaf auth-mismatch {
      type oc-yang:counter64;
      description
        "Count of the number of NTP packets received that were not
         processed due to authentication mismatch.";
    }
  }

  grouping system-ntp-top {
    description
      "Top-level grouping for configuration and state data for NTP";
    container ntp {
      description
        "Top-level container for NTP configuration and state";
      container config {
        description
          "Configuration data for NTP client.";
        uses system-ntp-config;
      }
      // NCS drop config false container state
      uses system-ntp-auth-keys-top;
      uses system-ntp-server-top;
    }
  }

  grouping system-routing-macaddr-config {
    description
      "Configuration data for system's routing MAC addresses.";
    leaf routing-mac {
      type oc-yang:mac-address;
      description
        "Any packets destined to this MAC address must be sent through the
         routing pipeline by the system. This MAC address is used to identify
         routed packets in addition to any other MAC addresses that the system
         may already have been using to perform routing.

         It is not expected that this MAC address will be used as the
         source MAC address of any routed packet, as the source MAC address of
         any packets generated by the system, or a MAC address used in ARP
         response. This MAC address may not be allocated from the block of
         MAC address that system owns. For instance, it's allocation could
         be managed by an external controller.";
    }
  }

  grouping system-macaddr-top {
    description
      "Top-level grouping for configuration and state of system's MAC addresses.";
    container mac-address {
      description
        "Top-level container for system's MAC address configuration and state";
      container config {
        description
          "Configuration data for routing MAC address.";
        uses system-routing-macaddr-config;
      }
      // NCS drop config false container state
    }
  }

  grouping system-memory-config {
    description
      "Configuration data for system memory";
  }

  grouping system-memory-state {
    description
      "Operational state data for system memory";
    leaf physical {
      type uint64;
      units "bytes";
      description
        "Reports the total physical memory available on the
         system.";
    }
    leaf reserved {
      type uint64;
      units "bytes";
      description
        "Memory reserved for system use";
    }
    leaf used {
      type uint64;
      units "bytes";
      description
        "Memory that has been used and not available for allocation.";
    }
    leaf free {
      type uint64;
      units "bytes";
      description
        "Memory that is not used and is available for allocation.";
    }
  }

  grouping system-memory-error-counters {
    description
      "Counters for system memory errors.";
    leaf correctable-ecc-errors {
      type uint64;
      description
        "Count of correctable ECC errors. Systems with ECC memory
         are capable of correcting Single-bit ECC errors.";
    }
    leaf uncorrectable-ecc-errors {
      type uint64;
      description
        "Count of uncorrectable ECC errors. Systems with ECC
         memory are capable of detecting multi-bit ECC errors,
         but cannot correct them.";
    }
    leaf total-ecc-errors {
      type uint64;
      description
        "Count of total ECC errors, this includes both correctable
         and uncorrectable ECC errors.";
    }
  }

  grouping system-memory-top {
    description
      "Top-level grouping for system memory data definitions";
    container memory {
      description
        "Top-level container for system memory data";
      container config {
        description
          "Configuration data for system memory";
        uses system-memory-config;
      }
      // NCS drop config false container state
    }
  }

  grouping system-cpu-state {
    description
      "Operational state data for the system CPU(s)";
    leaf index {
      type union {
        type enumeration {
          enum "ALL" {
            description
              "Index value indicating all CPUs in the system";
          }
        }
        type uint32;
      }
      description
        "The CPU index for each processor core on the system.  On a
         single-core system, the index should be zero.  The ALL
         index signifies an aggregation of the CPU utilization
         statistics over all cores in the system.";
    }
    container total {
      description
        "Total CPU utilization.";
      uses oc-types:avg-min-max-instant-stats-pct;
    }
    container user {
      description
        "Percentage of CPU time spent running in user space.";
      uses oc-types:avg-min-max-instant-stats-pct;
    }
    container kernel {
      description
        "Percentage of CPU time spent running in kernel space.";
      uses oc-types:avg-min-max-instant-stats-pct;
    }
    container nice {
      description
        "Percentage of CPU time spent running low-priority (niced)
         user processes.";
      uses oc-types:avg-min-max-instant-stats-pct;
    }
    container idle {
      description
        "Percentage of CPU time spent idle.";
      uses oc-types:avg-min-max-instant-stats-pct;
    }
    container wait {
      description
        "Percentage of CPU time spent waiting for I/O.";
      uses oc-types:avg-min-max-instant-stats-pct;
    }
    container hardware-interrupt {
      description
        "Percentage of CPU time spent servicing hardware interrupts.";
      uses oc-types:avg-min-max-instant-stats-pct;
    }
    container software-interrupt {
      description
        "Percentage of CPU time spent servicing software interrupts";
      uses oc-types:avg-min-max-instant-stats-pct;
    }
  }

  grouping system-cpu-top {
    description
      "Top-level grouping for system CPU data";
    // NCS drop config false container cpus
  }

  grouping system-top {
    description
      "Top level system data containers";
    container system {
      description
        "Enclosing container for system-related configuration and
         operational state data";
      container config {
        description
          "Global configuration data for the system";
        uses system-global-config;
      }
      // NCS drop config false container state
      uses mount-points-top;
      uses system-clock-top;
      uses system-dns-top;
      uses system-ntp-top;
      uses oc-sys-term:system-ssh-server-top;
      uses oc-sys-term:system-telnet-server-top;
      uses oc-log:logging-top;
      uses oc-aaa:aaa-top;
      uses system-memory-top;
      uses system-cpu-top;
      uses oc-proc:procmon-processes-top;
      uses oc-alarms:alarms-top;
      uses oc-messages:messages-top;
      uses oc-license:license-top;
      uses system-macaddr-top;
    }
  }

  augment "/ncs:devices/ncs:device/ncs:config" {
    uses system-top {
      refine system {
        tailf:ncs-device-type "netconf";
        tailf:display-when "not(../../ncs:module) or ../../ncs:module[ncs:name='openconfig-system']";
      }
    }
  }
  augment "/ncs:devices/ncs:device/ncs:live-status" {
    uses live_ncs_system-top {
      refine system {
        tailf:ncs-device-type "netconf";
        tailf:display-when "not(../../ncs:module) or ../../ncs:module[ncs:name='openconfig-system'] or (../../ncs:live-status-protocol[not(ncs:capability)]) or (../../ncs:live-status-protocol/ncs:capability/ncs:module[.='openconfig-system'])";
      }
    }
  }
  augment "/ncs:devices/ncs:template/ncs:ned-id/ncs:config" {
    uses ncs_template_system-top;
  }
  augment "/ncs:compliance/ncs:template/ncs:ned-id/ncs:config" {
    uses ncs_compliance_template_system-top;
  }

  identity NTP_AUTH_MD5 {
    base NTP_AUTH_TYPE;
    description
      "MD5 encryption method";
  }

  identity NTP_AUTH_TYPE {
    description
      "Base identity for encryption schemes supported for NTP
       authentication keys";
  }
}
