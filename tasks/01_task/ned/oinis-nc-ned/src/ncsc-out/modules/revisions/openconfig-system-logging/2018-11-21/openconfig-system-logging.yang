module openconfig-system-logging {
  // Generated by yanger -t ncs
  tailf:mount-id "oinis-nc-ned-nc-1.0:oinis-nc-ned-nc-1.0";
  tailf:ncs-device-type "netconf";

  yang-version 1;
  namespace "http://openconfig.net/yang/system/logging";
  prefix oc-log;

  import openconfig-extensions {
    prefix oc-ext;
  }
  import openconfig-inet-types {
    prefix oc-inet;
  }
  import tailf-common {
    prefix tailf;
  }
  import tailf-ncs {
    prefix ncs;
  }

  organization
    "OpenConfig working group";
  contact
    "OpenConfig working group
     www.openconfig.net";
  description
    "This module defines configuration and operational state data
     for common logging facilities on network systems.";
  oc-ext:openconfig-version "0.3.1";

  revision 2018-11-21 {
    description
      "Add OpenConfig module metadata extensions.";
    reference "0.3.1";
  }
  revision 2017-09-18 {
    description
      "Updated to use OpenConfig types modules";
    reference "0.3.0";
  }
  revision 2017-07-06 {
    description
      "Move to oc-inet types, add IETF attribution, add RADIUS
       counters, changed password leaf names to indicate hashed";
    reference "0.2.0";
  }
  revision 2017-01-29 {
    description
      "Initial public release";
    reference "0.1.0";
  }
  oc-ext:regexp-posix;
  oc-ext:catalog-organization "openconfig";
  oc-ext:origin "openconfig";

  typedef ncs_compliance_template_syslog-severity {
    type string;
    description
      "Syslog message severities";
    reference "IETF RFC 5424 - The Syslog Protocol";
  }

  typedef ncs_template_syslog-severity {
    type string;
    description
      "Syslog message severities";
    reference "IETF RFC 5424 - The Syslog Protocol";
  }

  typedef ncs_rpc_notif_syslog-severity {
    type enumeration {
      enum "EMERGENCY" {
        description
          "Emergency: system is unusable (0)";
      }
      enum "ALERT" {
        description
          "Alert: action must be taken immediately (1)";
      }
      enum "CRITICAL" {
        description
          "Critical: critical conditions (2)";
      }
      enum "ERROR" {
        description
          "Error: error conditions (3)";
      }
      enum "WARNING" {
        description
          "Warning: warning conditions (4)";
      }
      enum "NOTICE" {
        description
          "Notice: normal but significant  condition(5)";
      }
      enum "INFORMATIONAL" {
        description
          "Informational: informational messages (6)";
      }
      enum "DEBUG" {
        description
          "Debug: debug-level messages (7)";
      }
    }
    description
      "Syslog message severities";
    reference "IETF RFC 5424 - The Syslog Protocol";
  }

  typedef live_ncs_syslog-severity {
    type enumeration {
      enum "EMERGENCY" {
        description
          "Emergency: system is unusable (0)";
      }
      enum "ALERT" {
        description
          "Alert: action must be taken immediately (1)";
      }
      enum "CRITICAL" {
        description
          "Critical: critical conditions (2)";
      }
      enum "ERROR" {
        description
          "Error: error conditions (3)";
      }
      enum "WARNING" {
        description
          "Warning: warning conditions (4)";
      }
      enum "NOTICE" {
        description
          "Notice: normal but significant  condition(5)";
      }
      enum "INFORMATIONAL" {
        description
          "Informational: informational messages (6)";
      }
      enum "DEBUG" {
        description
          "Debug: debug-level messages (7)";
      }
    }
    description
      "Syslog message severities";
    reference "IETF RFC 5424 - The Syslog Protocol";
  }

  typedef syslog-severity {
    type enumeration {
      enum "EMERGENCY" {
        description
          "Emergency: system is unusable (0)";
      }
      enum "ALERT" {
        description
          "Alert: action must be taken immediately (1)";
      }
      enum "CRITICAL" {
        description
          "Critical: critical conditions (2)";
      }
      enum "ERROR" {
        description
          "Error: error conditions (3)";
      }
      enum "WARNING" {
        description
          "Warning: warning conditions (4)";
      }
      enum "NOTICE" {
        description
          "Notice: normal but significant  condition(5)";
      }
      enum "INFORMATIONAL" {
        description
          "Informational: informational messages (6)";
      }
      enum "DEBUG" {
        description
          "Debug: debug-level messages (7)";
      }
    }
    description
      "Syslog message severities";
    reference "IETF RFC 5424 - The Syslog Protocol";
  }

  grouping ncs_compliance_template_logging-selectors-config {
    description
      "Configuration data for logging selectors";
    leaf facility {
      type string;
      description
        "Specifies the facility, or class of messages to log";
    }
    leaf severity {
      type ncs_compliance_template_syslog-severity;
      description
        "Specifies that only messages of the given severity (or
         greater severity) for the corresonding facility are logged";
    }
  }

  grouping ncs_compliance_template_logging-selectors-state {
    description
      "Operational state data for logging selectors";
  }

  grouping ncs_compliance_template_logging-selectors-top {
    description
      "Top-level grouping for the logging selector list";
    container selectors {
      description
        "Enclosing container ";
      list selector {
        // NCS patched for predictable order
        ordered-by user;
        key "facility severity";
        description
          "List of selectors for log messages";
        leaf facility {
          type string;
          description
            "Reference to facility list key";
        }
        leaf severity {
          type string;
          description
            "Reference to severity list key";
        }
        container config {
          description
            "Configuration data ";
          uses ncs_compliance_template_logging-selectors-config;
        }
        // NCS drop config false container state
      }
    }
  }

  grouping ncs_compliance_template_logging-console-config {
    description
      "Configuration data for console logging";
  }

  grouping ncs_compliance_template_logging-console-state {
    description
      "Operational state data for console logging";
  }

  grouping ncs_compliance_template_logging-console-top {
    description
      "Top-level grouping for console logging data";
    container console {
      description
        "Top-level container for data related to console-based
         logging";
      container config {
        description
          "Configuration data for console logging";
        uses ncs_compliance_template_logging-console-config;
      }
      // NCS drop config false container state
      uses ncs_compliance_template_logging-selectors-top;
    }
  }

  grouping ncs_compliance_template_logging-remote-config {
    description
      "Configuration data for remote log servers";
    leaf host {
      type oc-inet:ncs_compliance_template_host;
      description
        "IP address or hostname of the remote log server";
    }
    leaf source-address {
      type oc-inet:ncs_compliance_template_ip-address;
      description
        "Source IP address for packets to the log server";
    }
    leaf remote-port {
      type oc-inet:ncs_compliance_template_port-number;
      // NCS drop default statement
      description
        "Sets the destination port number for syslog UDP messages to
         the server.  The default for syslog is 514.";
    }
  }

  grouping ncs_compliance_template_logging-remote-state {
    description
      "Operational state data for remote log servers";
  }

  grouping ncs_compliance_template_logging-remote-top {
    description
      "Top-level grouping for remote log servers";
    container remote-servers {
      description
        "Enclosing container for the list of remote log servers";
      list remote-server {
        // NCS patched for predictable order
        ordered-by user;
        key "host";
        description
          "List of remote log servers";
        leaf host {
          type string;
          description
            "Reference to the host list key";
        }
        container config {
          description
            "Configuration data for remote log servers";
          uses ncs_compliance_template_logging-remote-config;
        }
        // NCS drop config false container state
        uses ncs_compliance_template_logging-selectors-top;
      }
    }
  }

  grouping ncs_compliance_template_logging-top {
    description
      "Top-level grouping for logging data";
    container logging {
      description
        "Top-level container for data related to logging / syslog";
      uses ncs_compliance_template_logging-console-top;
      uses ncs_compliance_template_logging-remote-top;
    }
  }

  grouping ncs_template_logging-selectors-config {
    description
      "Configuration data for logging selectors";
    leaf facility {
      type string;
      description
        "Specifies the facility, or class of messages to log";
    }
    leaf severity {
      type ncs_template_syslog-severity;
      description
        "Specifies that only messages of the given severity (or
         greater severity) for the corresonding facility are logged";
    }
  }

  grouping ncs_template_logging-selectors-state {
    description
      "Operational state data for logging selectors";
  }

  grouping ncs_template_logging-selectors-top {
    description
      "Top-level grouping for the logging selector list";
    container selectors {
      description
        "Enclosing container ";
      list selector {
        // NCS patched for predictable order
        ordered-by user;
        key "facility severity";
        description
          "List of selectors for log messages";
        leaf facility {
          type string;
          description
            "Reference to facility list key";
        }
        leaf severity {
          type string;
          description
            "Reference to severity list key";
        }
        container config {
          description
            "Configuration data ";
          uses ncs_template_logging-selectors-config;
        }
        // NCS drop config false container state
      }
    }
  }

  grouping ncs_template_logging-console-config {
    description
      "Configuration data for console logging";
  }

  grouping ncs_template_logging-console-state {
    description
      "Operational state data for console logging";
  }

  grouping ncs_template_logging-console-top {
    description
      "Top-level grouping for console logging data";
    container console {
      description
        "Top-level container for data related to console-based
         logging";
      container config {
        description
          "Configuration data for console logging";
        uses ncs_template_logging-console-config;
      }
      // NCS drop config false container state
      uses ncs_template_logging-selectors-top;
    }
  }

  grouping ncs_template_logging-remote-config {
    description
      "Configuration data for remote log servers";
    leaf host {
      type oc-inet:ncs_template_host;
      description
        "IP address or hostname of the remote log server";
    }
    leaf source-address {
      type oc-inet:ncs_template_ip-address;
      description
        "Source IP address for packets to the log server";
    }
    leaf remote-port {
      type oc-inet:ncs_template_port-number;
      // NCS drop default statement
      description
        "Sets the destination port number for syslog UDP messages to
         the server.  The default for syslog is 514.";
    }
  }

  grouping ncs_template_logging-remote-state {
    description
      "Operational state data for remote log servers";
  }

  grouping ncs_template_logging-remote-top {
    description
      "Top-level grouping for remote log servers";
    container remote-servers {
      description
        "Enclosing container for the list of remote log servers";
      list remote-server {
        // NCS patched for predictable order
        ordered-by user;
        key "host";
        description
          "List of remote log servers";
        leaf host {
          type string;
          description
            "Reference to the host list key";
        }
        container config {
          description
            "Configuration data for remote log servers";
          uses ncs_template_logging-remote-config;
        }
        // NCS drop config false container state
        uses ncs_template_logging-selectors-top;
      }
    }
  }

  grouping ncs_template_logging-top {
    description
      "Top-level grouping for logging data";
    container logging {
      description
        "Top-level container for data related to logging / syslog";
      uses ncs_template_logging-console-top;
      uses ncs_template_logging-remote-top;
    }
  }

  grouping ncs_rpc_notif_logging-selectors-config {
    description
      "Configuration data for logging selectors";
    leaf facility {
      type identityref {
        base SYSLOG_FACILITY;
      }
      description
        "Specifies the facility, or class of messages to log";
    }
    leaf severity {
      type ncs_rpc_notif_syslog-severity;
      description
        "Specifies that only messages of the given severity (or
         greater severity) for the corresonding facility are logged";
    }
  }

  grouping ncs_rpc_notif_logging-selectors-state {
    description
      "Operational state data for logging selectors";
  }

  grouping ncs_rpc_notif_logging-selectors-top {
    description
      "Top-level grouping for the logging selector list";
    container selectors {
      description
        "Enclosing container ";
      list selector {
        key "facility severity";
        description
          "List of selectors for log messages";
        leaf facility {
          type leafref {
            path "../config/facility";
          }
          description
            "Reference to facility list key";
        }
        leaf severity {
          type leafref {
            path "../config/severity";
          }
          description
            "Reference to severity list key";
        }
        container config {
          description
            "Configuration data ";
          uses ncs_rpc_notif_logging-selectors-config;
        }
        container state {
          config false;
          description
            "Operational state data ";
          uses ncs_rpc_notif_logging-selectors-config;
          uses ncs_rpc_notif_logging-selectors-state;
        }
      }
    }
  }

  grouping ncs_rpc_notif_logging-console-config {
    description
      "Configuration data for console logging";
  }

  grouping ncs_rpc_notif_logging-console-state {
    description
      "Operational state data for console logging";
  }

  grouping ncs_rpc_notif_logging-console-top {
    description
      "Top-level grouping for console logging data";
    container console {
      description
        "Top-level container for data related to console-based
         logging";
      container config {
        description
          "Configuration data for console logging";
        uses ncs_rpc_notif_logging-console-config;
      }
      container state {
        config false;
        description
          "Operational state data for console logging";
        uses ncs_rpc_notif_logging-console-config;
        uses ncs_rpc_notif_logging-console-state;
      }
      uses ncs_rpc_notif_logging-selectors-top;
    }
  }

  grouping ncs_rpc_notif_logging-remote-config {
    description
      "Configuration data for remote log servers";
    leaf host {
      type oc-inet:ncs_rpc_notif_host;
      description
        "IP address or hostname of the remote log server";
    }
    leaf source-address {
      type oc-inet:ncs_rpc_notif_ip-address;
      description
        "Source IP address for packets to the log server";
    }
    leaf remote-port {
      type oc-inet:ncs_rpc_notif_port-number;
      default "514";
      description
        "Sets the destination port number for syslog UDP messages to
         the server.  The default for syslog is 514.";
    }
  }

  grouping ncs_rpc_notif_logging-remote-state {
    description
      "Operational state data for remote log servers";
  }

  grouping ncs_rpc_notif_logging-remote-top {
    description
      "Top-level grouping for remote log servers";
    container remote-servers {
      description
        "Enclosing container for the list of remote log servers";
      list remote-server {
        key "host";
        description
          "List of remote log servers";
        leaf host {
          type leafref {
            path "../config/host";
          }
          description
            "Reference to the host list key";
        }
        container config {
          description
            "Configuration data for remote log servers";
          uses ncs_rpc_notif_logging-remote-config;
        }
        container state {
          config false;
          description
            "Operational state data for remote log servers";
          uses ncs_rpc_notif_logging-remote-config;
          uses ncs_rpc_notif_logging-remote-state;
        }
        uses ncs_rpc_notif_logging-selectors-top;
      }
    }
  }

  grouping ncs_rpc_notif_logging-top {
    description
      "Top-level grouping for logging data";
    container logging {
      description
        "Top-level container for data related to logging / syslog";
      uses ncs_rpc_notif_logging-console-top;
      uses ncs_rpc_notif_logging-remote-top;
    }
  }

  grouping live_ncs_logging-selectors-config {
    description
      "Configuration data for logging selectors";
    leaf facility {
      type identityref {
        base SYSLOG_FACILITY;
      }
      description
        "Specifies the facility, or class of messages to log";
    }
    leaf severity {
      type live_ncs_syslog-severity;
      description
        "Specifies that only messages of the given severity (or
         greater severity) for the corresonding facility are logged";
    }
  }

  grouping live_ncs_logging-selectors-state {
    description
      "Operational state data for logging selectors";
  }

  grouping live_ncs_logging-selectors-top {
    description
      "Top-level grouping for the logging selector list";
    container selectors {
      description
        "Enclosing container ";
      list selector {
        key "facility severity";
        description
          "List of selectors for log messages";
        leaf facility {
          type leafref {
            path "../config/facility";
          }
          description
            "Reference to facility list key";
        }
        leaf severity {
          type leafref {
            path "../config/severity";
          }
          description
            "Reference to severity list key";
        }
        container config {
          description
            "Configuration data ";
          uses live_ncs_logging-selectors-config;
        }
        container state {
          description
            "Operational state data ";
          uses live_ncs_logging-selectors-config;
          uses live_ncs_logging-selectors-state;
        }
      }
    }
  }

  grouping live_ncs_logging-console-config {
    description
      "Configuration data for console logging";
  }

  grouping live_ncs_logging-console-state {
    description
      "Operational state data for console logging";
  }

  grouping live_ncs_logging-console-top {
    description
      "Top-level grouping for console logging data";
    container console {
      description
        "Top-level container for data related to console-based
         logging";
      container config {
        description
          "Configuration data for console logging";
        uses live_ncs_logging-console-config;
      }
      container state {
        description
          "Operational state data for console logging";
        uses live_ncs_logging-console-config;
        uses live_ncs_logging-console-state;
      }
      uses live_ncs_logging-selectors-top;
    }
  }

  grouping live_ncs_logging-remote-config {
    description
      "Configuration data for remote log servers";
    leaf host {
      type oc-inet:live_ncs_host;
      description
        "IP address or hostname of the remote log server";
    }
    leaf source-address {
      type oc-inet:live_ncs_ip-address;
      description
        "Source IP address for packets to the log server";
    }
    leaf remote-port {
      type oc-inet:live_ncs_port-number;
      // NCS drop default statement
      description
        "Sets the destination port number for syslog UDP messages to
         the server.  The default for syslog is 514.";
    }
  }

  grouping live_ncs_logging-remote-state {
    description
      "Operational state data for remote log servers";
  }

  grouping live_ncs_logging-remote-top {
    description
      "Top-level grouping for remote log servers";
    container remote-servers {
      description
        "Enclosing container for the list of remote log servers";
      list remote-server {
        key "host";
        description
          "List of remote log servers";
        leaf host {
          type leafref {
            path "../config/host";
          }
          description
            "Reference to the host list key";
        }
        container config {
          description
            "Configuration data for remote log servers";
          uses live_ncs_logging-remote-config;
        }
        container state {
          description
            "Operational state data for remote log servers";
          uses live_ncs_logging-remote-config;
          uses live_ncs_logging-remote-state;
        }
        uses live_ncs_logging-selectors-top;
      }
    }
  }

  grouping live_ncs_logging-top {
    description
      "Top-level grouping for logging data";
    container logging {
      description
        "Top-level container for data related to logging / syslog";
      uses live_ncs_logging-console-top;
      uses live_ncs_logging-remote-top;
    }
  }

  grouping logging-selectors-config {
    description
      "Configuration data for logging selectors";
    leaf facility {
      type identityref {
        base SYSLOG_FACILITY;
      }
      description
        "Specifies the facility, or class of messages to log";
    }
    leaf severity {
      type syslog-severity;
      description
        "Specifies that only messages of the given severity (or
         greater severity) for the corresonding facility are logged";
    }
  }

  grouping logging-selectors-state {
    description
      "Operational state data for logging selectors";
  }

  grouping logging-selectors-top {
    description
      "Top-level grouping for the logging selector list";
    container selectors {
      description
        "Enclosing container ";
      list selector {
        key "facility severity";
        description
          "List of selectors for log messages";
        leaf facility {
          type leafref {
            path "../config/facility";
          }
          description
            "Reference to facility list key";
        }
        leaf severity {
          type leafref {
            path "../config/severity";
          }
          description
            "Reference to severity list key";
        }
        container config {
          description
            "Configuration data ";
          uses logging-selectors-config;
        }
        // NCS drop config false container state
      }
    }
  }

  grouping logging-console-config {
    description
      "Configuration data for console logging";
  }

  grouping logging-console-state {
    description
      "Operational state data for console logging";
  }

  grouping logging-console-top {
    description
      "Top-level grouping for console logging data";
    container console {
      description
        "Top-level container for data related to console-based
         logging";
      container config {
        description
          "Configuration data for console logging";
        uses logging-console-config;
      }
      // NCS drop config false container state
      uses logging-selectors-top;
    }
  }

  grouping logging-remote-config {
    description
      "Configuration data for remote log servers";
    leaf host {
      type oc-inet:host;
      description
        "IP address or hostname of the remote log server";
    }
    leaf source-address {
      type oc-inet:ip-address;
      description
        "Source IP address for packets to the log server";
    }
    leaf remote-port {
      type oc-inet:port-number;
      default "514";
      description
        "Sets the destination port number for syslog UDP messages to
         the server.  The default for syslog is 514.";
    }
  }

  grouping logging-remote-state {
    description
      "Operational state data for remote log servers";
  }

  grouping logging-remote-top {
    description
      "Top-level grouping for remote log servers";
    container remote-servers {
      description
        "Enclosing container for the list of remote log servers";
      list remote-server {
        key "host";
        description
          "List of remote log servers";
        leaf host {
          type leafref {
            path "../config/host";
          }
          description
            "Reference to the host list key";
        }
        container config {
          description
            "Configuration data for remote log servers";
          uses logging-remote-config;
        }
        // NCS drop config false container state
        uses logging-selectors-top;
      }
    }
  }

  grouping logging-top {
    description
      "Top-level grouping for logging data";
    container logging {
      description
        "Top-level container for data related to logging / syslog";
      uses logging-console-top;
      uses logging-remote-top;
    }
  }

  identity DEST_REMOTE {
    base LOG_DESTINATION_TYPE;
    description
      "Directs log messages to a remote syslog server";
  }

  identity DEST_FILE {
    base LOG_DESTINATION_TYPE;
    description
      "Directs log messages to a local file";
  }

  identity DEST_BUFFER {
    base LOG_DESTINATION_TYPE;
    description
      "Directs log messages to and in-memory circular buffer";
  }

  identity DEST_CONSOLE {
    base LOG_DESTINATION_TYPE;
    description
      "Directs log messages to the console";
  }

  identity LOG_DESTINATION_TYPE {
    description
      "Base identity for destination for logging messages";
  }

  identity LOCAL7 {
    base SYSLOG_FACILITY;
    description
      "The facility for local use 7 messages.";
    reference "IETF RFC 5424 - The Syslog Protocol";
  }

  identity LOCAL6 {
    base SYSLOG_FACILITY;
    description
      "The facility for local use 6 messages.";
    reference "IETF RFC 5424 - The Syslog Protocol";
  }

  identity LOCAL5 {
    base SYSLOG_FACILITY;
    description
      "The facility for local use 5 messages.";
    reference "IETF RFC 5424 - The Syslog Protocol";
  }

  identity LOCAL4 {
    base SYSLOG_FACILITY;
    description
      "The facility for local use 4 messages.";
    reference "IETF RFC 5424 - The Syslog Protocol";
  }

  identity LOCAL3 {
    base SYSLOG_FACILITY;
    description
      "The facility for local use 3 messages.";
    reference "IETF RFC 5424 - The Syslog Protocol";
  }

  identity LOCAL2 {
    base SYSLOG_FACILITY;
    description
      "The facility for local use 2 messages.";
    reference "IETF RFC 5424 - The Syslog Protocol";
  }

  identity LOCAL1 {
    base SYSLOG_FACILITY;
    description
      "The facility for local use 1 messages.";
    reference "IETF RFC 5424 - The Syslog Protocol";
  }

  identity LOCAL0 {
    base SYSLOG_FACILITY;
    description
      "The facility for local use 0 messages.";
    reference "IETF RFC 5424 - The Syslog Protocol";
  }

  identity CONSOLE {
    base SYSLOG_FACILITY;
    description
      "The facility for log alert messages.";
    reference "IETF RFC 5424 - The Syslog Protocol";
  }

  identity AUDIT {
    base SYSLOG_FACILITY;
    description
      "The facility for log audit messages.";
    reference "IETF RFC 5424 - The Syslog Protocol";
  }

  identity NTP {
    base SYSLOG_FACILITY;
    description
      "The facility for the NTP subsystem.";
    reference "IETF RFC 5424 - The Syslog Protocol";
  }

  identity AUTHPRIV {
    base SYSLOG_FACILITY;
    description
      "The facility for privileged security/authorization messages.";
    reference "IETF RFC 5424 - The Syslog Protocol";
  }

  identity SYSLOG {
    base SYSLOG_FACILITY;
    description
      "The facility for messages generated internally by syslogd
       facility.";
    reference "IETF RFC 5424 - The Syslog Protocol";
  }

  identity AUTH {
    base SYSLOG_FACILITY;
    description
      "The facility for security/authorization messages.";
    reference "IETF RFC 5424 - The Syslog Protocol";
  }

  identity SYSTEM_DAEMON {
    base SYSLOG_FACILITY;
    description
      "The facility for the system daemons.";
    reference "IETF RFC 5424 - The Syslog Protocol";
  }

  identity MAIL {
    base SYSLOG_FACILITY;
    description
      "The facility for the mail system.";
    reference "IETF RFC 5424 - The Syslog Protocol";
  }

  identity USER {
    base SYSLOG_FACILITY;
    description
      "The facility for user-level messages.";
    reference "IETF RFC 5424 - The Syslog Protocol";
  }

  identity KERNEL {
    base SYSLOG_FACILITY;
    description
      "The facility for kernel messages";
    reference "IETF RFC 5424 - The Syslog Protocol";
  }

  identity ALL {
    base SYSLOG_FACILITY;
    description
      "All supported facilities";
  }

  identity SYSLOG_FACILITY {
    description
      "Base identity for Syslog message facilities.";
    reference "IETF RFC 5424 - The Syslog Protocol";
  }
}
