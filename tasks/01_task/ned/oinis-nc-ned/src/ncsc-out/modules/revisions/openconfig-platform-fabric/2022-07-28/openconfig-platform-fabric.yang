module openconfig-platform-fabric {
  // Generated by yanger -t ncs
  tailf:mount-id "oinis-nc-ned-nc-1.0:oinis-nc-ned-nc-1.0";
  tailf:ncs-device-type "netconf";

  yang-version 1;
  namespace "http://openconfig.net/yang/platform/fabric";
  prefix oc-fabric;

  import openconfig-platform {
    prefix oc-platform;
  }
  import openconfig-extensions {
    prefix oc-ext;
  }
  import tailf-common {
    prefix tailf;
  }
  import tailf-ncs {
    prefix ncs;
  }

  organization
    "OpenConfig working group";
  contact
    "OpenConfig working group
     www.openconfig.net";
  description
    "This module defines data related to FABRIC components in
     the openconfig-platform model";
  oc-ext:openconfig-version "0.1.0";

  revision 2022-07-28 {
    description
      "Initial revision";
    reference "0.1.0";
  }
  oc-ext:catalog-organization "openconfig";
  oc-ext:origin "openconfig";

  grouping ncs_compliance_template_fabric-config {
    description
      "Configuration data for fabric components";
    uses oc-platform:ncs_compliance_template_component-power-management;
  }

  grouping ncs_template_fabric-config {
    description
      "Configuration data for fabric components";
    uses oc-platform:ncs_template_component-power-management;
  }

  grouping ncs_rpc_notif_fabric-config {
    description
      "Configuration data for fabric components";
    uses oc-platform:ncs_rpc_notif_component-power-management;
  }

  grouping live_ncs_fabric-config {
    description
      "Configuration data for fabric components";
    uses oc-platform:live_ncs_component-power-management;
  }

  grouping fabric-config {
    description
      "Configuration data for fabric components";
    uses oc-platform:component-power-management;
  }

  augment "/ncs:compliance/ncs:template/ncs:ned-id/ncs:config/oc-platform:components/oc-platform:component/oc-platform:fabric/oc-platform:config" {
    description
      "Adding fabric data to physical inventory. This subtree
       is only valid when the type of the component is FABRIC.";
    uses ncs_compliance_template_fabric-config;
  }
  augment "/ncs:devices/ncs:template/ncs:ned-id/ncs:config/oc-platform:components/oc-platform:component/oc-platform:fabric/oc-platform:config" {
    description
      "Adding fabric data to physical inventory. This subtree
       is only valid when the type of the component is FABRIC.";
    uses ncs_template_fabric-config;
  }
  augment "/ncs:devices/ncs:device/ncs:live-status/oc-platform:components/oc-platform:component/oc-platform:fabric/oc-platform:config" {
    description
      "Adding fabric data to physical inventory. This subtree
       is only valid when the type of the component is FABRIC.";
    uses live_ncs_fabric-config {
      refine power-admin-state {
        tailf:ncs-device-type "netconf";
        tailf:display-when "not(../../../../../../ncs:module) or ../../../../../../ncs:module[ncs:name='openconfig-platform-fabric'] or (../../../../../../ncs:live-status-protocol[not(ncs:capability)]) or (../../../../../../ncs:live-status-protocol/ncs:capability/ncs:module[.='openconfig-platform-fabric'])";
      }
    }
  }
  augment "/ncs:devices/ncs:device/ncs:config/oc-platform:components/oc-platform:component/oc-platform:fabric/oc-platform:config" {
    description
      "Adding fabric data to physical inventory. This subtree
       is only valid when the type of the component is FABRIC.";
    uses fabric-config {
      refine power-admin-state {
        tailf:ncs-device-type "netconf";
        tailf:display-when "not(../../../../../../ncs:module) or ../../../../../../ncs:module[ncs:name='openconfig-platform-fabric']";
      }
    }
  }
  augment "/ncs:devices/ncs:device/ncs:live-status/oc-platform:components/oc-platform:component/oc-platform:fabric/oc-platform:state" {
    description
      "Adding fabric data to physical inventory. This subtree
       is only valid when the type of the component is FABRIC.";
    uses live_ncs_fabric-config {
      refine power-admin-state {
        tailf:ncs-device-type "netconf";
        tailf:display-when "not(../../../../../../ncs:module) or ../../../../../../ncs:module[ncs:name='openconfig-platform-fabric'] or (../../../../../../ncs:live-status-protocol[not(ncs:capability)]) or (../../../../../../ncs:live-status-protocol/ncs:capability/ncs:module[.='openconfig-platform-fabric'])";
      }
    }
  }
}
