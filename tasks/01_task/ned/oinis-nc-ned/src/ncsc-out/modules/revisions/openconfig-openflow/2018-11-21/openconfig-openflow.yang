module openconfig-openflow {
  // Generated by yanger -t ncs
  tailf:mount-id "oinis-nc-ned-nc-1.0:oinis-nc-ned-nc-1.0";
  tailf:ncs-device-type "netconf";

  yang-version 1;
  namespace "http://openconfig.net/yang/openflow";
  prefix openflow;

  import openconfig-extensions {
    prefix oc-ext;
  }
  import openconfig-inet-types {
    prefix oc-inet;
  }
  import openconfig-interfaces {
    prefix oc-if;
  }
  import openconfig-openflow-types {
    prefix of-types;
  }
  import openconfig-system {
    prefix oc-sys;
  }
  import tailf-common {
    prefix tailf;
  }
  import tailf-ncs {
    prefix ncs;
  }

  organization
    "OpenConfig working group";
  contact
    "OpenConfig working group
     www.openconfig.net";
  description
    "This module defines configuration and operational state data for
     Openflow.";
  oc-ext:openconfig-version "0.1.2";

  revision 2018-11-21 {
    description
      "Add OpenConfig module metadata extensions.";
    reference "0.1.2";
  }
  revision 2017-08-24 {
    description
      "Minor formatting fixes.Initial revision";
    reference "0.1.1";
  }
  revision 2017-06-01 {
    description
      "Initial revision";
    reference "0.1.0";
  }
  oc-ext:regexp-posix;
  oc-ext:catalog-organization "openconfig";
  oc-ext:origin "openconfig";

  grouping ncs_compliance_template_openflow-controller-config {
    description
      "Openflow controller config";
    leaf name {
      type string;
      description
        "Name of this Openflow controller. All connections
         for the same controller need to have the same name.";
    }
  }

  grouping ncs_compliance_template_openflow-controller-state {
    description
      "Openflow controller state";
  }

  grouping ncs_compliance_template_openflow-controllers-top {
    description
      "Top-level for the Openflow controllers model";
    container controllers {
      description
        "Container for the Openflow controllers model";
      list controller {
        // NCS patched for predictable order
        ordered-by user;
        key "name";
        description
          "The Openflow Switch connects to all Openflow controllers
           configured";
        leaf name {
          type string;
          description
            "The name identifies the controller.";
        }
        container config {
          description
            "Container for the Openflow controller config.";
          uses ncs_compliance_template_openflow-controller-config;
        }
        // NCS drop config false container state
        uses ncs_compliance_template_openflow-connections-top;
      }
    }
  }

  grouping ncs_compliance_template_openflow-connections-config {
    description
      "Configuration data for OpenFlow controller connections";
    leaf aux-id {
      type of-types:ncs_compliance_template_auxiliary-id;
      description
        "Controller auxiliary ID. Must be 0 for the main controller.
         One controller may have multiple auxiliary connections as
         specified by the Openflow protocol. Besides configuring the
         main controller, it is also possible to configure auxiliary
         connections. The main controller must have the aux-id
         set to zero. All others must have an aux-id different
         from 0.";
    }
    leaf priority {
      type string;
      description
        "Optional value for servicing auxiliary connections with
         different priorities.";
    }
    leaf address {
      type oc-inet:ncs_compliance_template_ip-address;
      description
        "The IP address of the controller.";
    }
    leaf port {
      type oc-inet:ncs_compliance_template_port-number;
      // NCS drop default statement
      description
        "Controller port to use.";
    }
    leaf transport {
      type of-types:ncs_compliance_template_transport;
      // NCS drop default statement
      description
        "Controller transport protocol used.";
    }
    leaf certificate-id {
      type string;
      description
        "Certificate ID is used for TLS connections. When installed,
         certificates are associated with an ID. This ID specifies the
         certificate to use in a TLS connection.";
    }
    leaf source-interface {
      type oc-if:ncs_compliance_template_base-interface-ref;
      description
        "Optionally specify the source interface for the
         controller connection.";
    }
  }

  grouping ncs_compliance_template_openflow-connections-state {
    description
      "Operational state data for OpenFlow controller connections";
    leaf connected {
      type string;
      description
        "When set to true, indicates the connection between the
         switch and controller is established.";
    }
  }

  grouping ncs_compliance_template_openflow-connections-top {
    description
      "Top-level grouping for OpenFlow controller connections";
    container connections {
      description
        "Enclosing container for list of controller connections";
      list connection {
        // NCS patched for predictable order
        ordered-by user;
        key "aux-id";
        description
          "List of connections to the OpenFlow controller.
           The Openflow switch always connects to configured Openflow
           controllers. Each controller can have more than one
           connection, called auxiliary Openflow connections.";
        leaf aux-id {
          type string;
          description
            "Reference to auxiliary id list key";
        }
        container config {
          description
            "Configuration data for OpenFlow controller connections";
          uses ncs_compliance_template_openflow-connections-config;
        }
        // NCS drop config false container state
      }
    }
  }

  grouping ncs_compliance_template_openflow-agent-config {
    description
      "Openflow agent config";
    leaf datapath-id {
      type of-types:ncs_compliance_template_datapath-id;
      description
        "Datapath unique ID. The lower 48-bits are for
         a MAC address, while the upper 16-bits are
         implementer-defined.";
    }
    leaf failure-mode {
      type of-types:ncs_compliance_template_failure-mode;
      description
        "Failure mode for Openflow.";
    }
    leaf backoff-interval {
      type string;
      units "seconds";
      description
        "Openflow agent connection backoff interval.";
    }
    leaf max-backoff {
      type string;
      units "seconds";
      description
        "Openflow agent max backoff time.";
    }
    leaf inactivity-probe {
      type string;
      units "seconds";
      description
        "Openflow agent inactivity probe period.";
    }
  }

  grouping ncs_compliance_template_openflow-agent-state {
    description
      "Openflow agent state";
  }

  grouping ncs_compliance_template_openflow-agent-top {
    description
      "Top-level for the Openflow agent model";
    container agent {
      description
        "Container for the Openflow agent model.";
      container config {
        description
          "Container for the Openflow agent config.";
        uses ncs_compliance_template_openflow-agent-config;
      }
      // NCS drop config false container state
    }
  }

  grouping ncs_compliance_template_openflow-top {
    description
      "Top-level for the Openflow model";
    container openflow {
      description
        "Container for Openflow model";
      uses ncs_compliance_template_openflow-controllers-top;
      uses ncs_compliance_template_openflow-agent-top;
    }
  }

  grouping ncs_template_openflow-controller-config {
    description
      "Openflow controller config";
    leaf name {
      type string;
      description
        "Name of this Openflow controller. All connections
         for the same controller need to have the same name.";
    }
  }

  grouping ncs_template_openflow-controller-state {
    description
      "Openflow controller state";
  }

  grouping ncs_template_openflow-controllers-top {
    description
      "Top-level for the Openflow controllers model";
    container controllers {
      description
        "Container for the Openflow controllers model";
      list controller {
        // NCS patched for predictable order
        ordered-by user;
        key "name";
        description
          "The Openflow Switch connects to all Openflow controllers
           configured";
        leaf name {
          type string;
          description
            "The name identifies the controller.";
        }
        container config {
          description
            "Container for the Openflow controller config.";
          uses ncs_template_openflow-controller-config;
        }
        // NCS drop config false container state
        uses ncs_template_openflow-connections-top;
      }
    }
  }

  grouping ncs_template_openflow-connections-config {
    description
      "Configuration data for OpenFlow controller connections";
    leaf aux-id {
      type of-types:ncs_template_auxiliary-id;
      description
        "Controller auxiliary ID. Must be 0 for the main controller.
         One controller may have multiple auxiliary connections as
         specified by the Openflow protocol. Besides configuring the
         main controller, it is also possible to configure auxiliary
         connections. The main controller must have the aux-id
         set to zero. All others must have an aux-id different
         from 0.";
    }
    leaf priority {
      type string;
      description
        "Optional value for servicing auxiliary connections with
         different priorities.";
    }
    leaf address {
      type oc-inet:ncs_template_ip-address;
      description
        "The IP address of the controller.";
    }
    leaf port {
      type oc-inet:ncs_template_port-number;
      // NCS drop default statement
      description
        "Controller port to use.";
    }
    leaf transport {
      type of-types:ncs_template_transport;
      // NCS drop default statement
      description
        "Controller transport protocol used.";
    }
    leaf certificate-id {
      type string;
      description
        "Certificate ID is used for TLS connections. When installed,
         certificates are associated with an ID. This ID specifies the
         certificate to use in a TLS connection.";
    }
    leaf source-interface {
      type oc-if:ncs_template_base-interface-ref;
      description
        "Optionally specify the source interface for the
         controller connection.";
    }
  }

  grouping ncs_template_openflow-connections-state {
    description
      "Operational state data for OpenFlow controller connections";
    leaf connected {
      type string;
      description
        "When set to true, indicates the connection between the
         switch and controller is established.";
    }
  }

  grouping ncs_template_openflow-connections-top {
    description
      "Top-level grouping for OpenFlow controller connections";
    container connections {
      description
        "Enclosing container for list of controller connections";
      list connection {
        // NCS patched for predictable order
        ordered-by user;
        key "aux-id";
        description
          "List of connections to the OpenFlow controller.
           The Openflow switch always connects to configured Openflow
           controllers. Each controller can have more than one
           connection, called auxiliary Openflow connections.";
        leaf aux-id {
          type string;
          description
            "Reference to auxiliary id list key";
        }
        container config {
          description
            "Configuration data for OpenFlow controller connections";
          uses ncs_template_openflow-connections-config;
        }
        // NCS drop config false container state
      }
    }
  }

  grouping ncs_template_openflow-agent-config {
    description
      "Openflow agent config";
    leaf datapath-id {
      type of-types:ncs_template_datapath-id;
      description
        "Datapath unique ID. The lower 48-bits are for
         a MAC address, while the upper 16-bits are
         implementer-defined.";
    }
    leaf failure-mode {
      type of-types:ncs_template_failure-mode;
      description
        "Failure mode for Openflow.";
    }
    leaf backoff-interval {
      type string;
      units "seconds";
      description
        "Openflow agent connection backoff interval.";
    }
    leaf max-backoff {
      type string;
      units "seconds";
      description
        "Openflow agent max backoff time.";
    }
    leaf inactivity-probe {
      type string;
      units "seconds";
      description
        "Openflow agent inactivity probe period.";
    }
  }

  grouping ncs_template_openflow-agent-state {
    description
      "Openflow agent state";
  }

  grouping ncs_template_openflow-agent-top {
    description
      "Top-level for the Openflow agent model";
    container agent {
      description
        "Container for the Openflow agent model.";
      container config {
        description
          "Container for the Openflow agent config.";
        uses ncs_template_openflow-agent-config;
      }
      // NCS drop config false container state
    }
  }

  grouping ncs_template_openflow-top {
    description
      "Top-level for the Openflow model";
    container openflow {
      description
        "Container for Openflow model";
      uses ncs_template_openflow-controllers-top;
      uses ncs_template_openflow-agent-top;
    }
  }

  grouping ncs_rpc_notif_openflow-controller-config {
    description
      "Openflow controller config";
    leaf name {
      type string;
      description
        "Name of this Openflow controller. All connections
         for the same controller need to have the same name.";
    }
  }

  grouping ncs_rpc_notif_openflow-controller-state {
    description
      "Openflow controller state";
  }

  grouping ncs_rpc_notif_openflow-controllers-top {
    description
      "Top-level for the Openflow controllers model";
    container controllers {
      description
        "Container for the Openflow controllers model";
      list controller {
        key "name";
        description
          "The Openflow Switch connects to all Openflow controllers
           configured";
        leaf name {
          type leafref {
            path "../config/name";
          }
          description
            "The name identifies the controller.";
        }
        container config {
          description
            "Container for the Openflow controller config.";
          uses ncs_rpc_notif_openflow-controller-config;
        }
        container state {
          config false;
          description
            "Container for the Openflow controller state.";
          uses ncs_rpc_notif_openflow-controller-config;
          uses ncs_rpc_notif_openflow-controller-state;
        }
        uses ncs_rpc_notif_openflow-connections-top;
      }
    }
  }

  grouping ncs_rpc_notif_openflow-connections-config {
    description
      "Configuration data for OpenFlow controller connections";
    leaf aux-id {
      type of-types:ncs_rpc_notif_auxiliary-id;
      description
        "Controller auxiliary ID. Must be 0 for the main controller.
         One controller may have multiple auxiliary connections as
         specified by the Openflow protocol. Besides configuring the
         main controller, it is also possible to configure auxiliary
         connections. The main controller must have the aux-id
         set to zero. All others must have an aux-id different
         from 0.";
    }
    leaf priority {
      type uint8;
      description
        "Optional value for servicing auxiliary connections with
         different priorities.";
    }
    leaf address {
      type oc-inet:ncs_rpc_notif_ip-address;
      description
        "The IP address of the controller.";
    }
    leaf port {
      type oc-inet:ncs_rpc_notif_port-number;
      default "6653";
      description
        "Controller port to use.";
    }
    leaf transport {
      type of-types:ncs_rpc_notif_transport;
      default "TCP";
      description
        "Controller transport protocol used.";
    }
    leaf certificate-id {
      type string;
      description
        "Certificate ID is used for TLS connections. When installed,
         certificates are associated with an ID. This ID specifies the
         certificate to use in a TLS connection.";
    }
    leaf source-interface {
      type oc-if:ncs_rpc_notif_base-interface-ref;
      description
        "Optionally specify the source interface for the
         controller connection.";
    }
  }

  grouping ncs_rpc_notif_openflow-connections-state {
    description
      "Operational state data for OpenFlow controller connections";
    leaf connected {
      type boolean;
      description
        "When set to true, indicates the connection between the
         switch and controller is established.";
    }
  }

  grouping ncs_rpc_notif_openflow-connections-top {
    description
      "Top-level grouping for OpenFlow controller connections";
    container connections {
      description
        "Enclosing container for list of controller connections";
      list connection {
        key "aux-id";
        description
          "List of connections to the OpenFlow controller.
           The Openflow switch always connects to configured Openflow
           controllers. Each controller can have more than one
           connection, called auxiliary Openflow connections.";
        leaf aux-id {
          type leafref {
            path "../config/aux-id";
          }
          description
            "Reference to auxiliary id list key";
        }
        container config {
          description
            "Configuration data for OpenFlow controller connections";
          uses ncs_rpc_notif_openflow-connections-config;
        }
        container state {
          config false;
          description
            "Operational state data for OpenFlow controller
             connections";
          uses ncs_rpc_notif_openflow-connections-config;
          uses ncs_rpc_notif_openflow-connections-state;
        }
      }
    }
  }

  grouping ncs_rpc_notif_openflow-agent-config {
    description
      "Openflow agent config";
    leaf datapath-id {
      type of-types:ncs_rpc_notif_datapath-id;
      description
        "Datapath unique ID. The lower 48-bits are for
         a MAC address, while the upper 16-bits are
         implementer-defined.";
    }
    leaf failure-mode {
      type of-types:ncs_rpc_notif_failure-mode;
      description
        "Failure mode for Openflow.";
    }
    leaf backoff-interval {
      type uint32;
      units "seconds";
      description
        "Openflow agent connection backoff interval.";
    }
    leaf max-backoff {
      type uint32;
      units "seconds";
      description
        "Openflow agent max backoff time.";
    }
    leaf inactivity-probe {
      type uint32;
      units "seconds";
      description
        "Openflow agent inactivity probe period.";
    }
  }

  grouping ncs_rpc_notif_openflow-agent-state {
    description
      "Openflow agent state";
  }

  grouping ncs_rpc_notif_openflow-agent-top {
    description
      "Top-level for the Openflow agent model";
    container agent {
      description
        "Container for the Openflow agent model.";
      container config {
        description
          "Container for the Openflow agent config.";
        uses ncs_rpc_notif_openflow-agent-config;
      }
      container state {
        config false;
        description
          "Container for the Openflow agent state.";
        uses ncs_rpc_notif_openflow-agent-config;
        uses ncs_rpc_notif_openflow-agent-state;
      }
    }
  }

  grouping ncs_rpc_notif_openflow-top {
    description
      "Top-level for the Openflow model";
    container openflow {
      description
        "Container for Openflow model";
      uses ncs_rpc_notif_openflow-controllers-top;
      uses ncs_rpc_notif_openflow-agent-top;
    }
  }

  grouping live_ncs_openflow-controller-config {
    description
      "Openflow controller config";
    leaf name {
      type string;
      description
        "Name of this Openflow controller. All connections
         for the same controller need to have the same name.";
    }
  }

  grouping live_ncs_openflow-controller-state {
    description
      "Openflow controller state";
  }

  grouping live_ncs_openflow-controllers-top {
    description
      "Top-level for the Openflow controllers model";
    container controllers {
      description
        "Container for the Openflow controllers model";
      list controller {
        key "name";
        description
          "The Openflow Switch connects to all Openflow controllers
           configured";
        leaf name {
          type leafref {
            path "../config/name";
          }
          description
            "The name identifies the controller.";
        }
        container config {
          description
            "Container for the Openflow controller config.";
          uses live_ncs_openflow-controller-config;
        }
        container state {
          description
            "Container for the Openflow controller state.";
          uses live_ncs_openflow-controller-config;
          uses live_ncs_openflow-controller-state;
        }
        uses live_ncs_openflow-connections-top;
      }
    }
  }

  grouping live_ncs_openflow-connections-config {
    description
      "Configuration data for OpenFlow controller connections";
    leaf aux-id {
      type of-types:live_ncs_auxiliary-id;
      description
        "Controller auxiliary ID. Must be 0 for the main controller.
         One controller may have multiple auxiliary connections as
         specified by the Openflow protocol. Besides configuring the
         main controller, it is also possible to configure auxiliary
         connections. The main controller must have the aux-id
         set to zero. All others must have an aux-id different
         from 0.";
    }
    leaf priority {
      type uint8;
      description
        "Optional value for servicing auxiliary connections with
         different priorities.";
    }
    leaf address {
      type oc-inet:live_ncs_ip-address;
      description
        "The IP address of the controller.";
    }
    leaf port {
      type oc-inet:live_ncs_port-number;
      // NCS drop default statement
      description
        "Controller port to use.";
    }
    leaf transport {
      type of-types:live_ncs_transport;
      // NCS drop default statement
      description
        "Controller transport protocol used.";
    }
    leaf certificate-id {
      type string;
      description
        "Certificate ID is used for TLS connections. When installed,
         certificates are associated with an ID. This ID specifies the
         certificate to use in a TLS connection.";
    }
    leaf source-interface {
      type oc-if:live_ncs_base-interface-ref;
      description
        "Optionally specify the source interface for the
         controller connection.";
    }
  }

  grouping live_ncs_openflow-connections-state {
    description
      "Operational state data for OpenFlow controller connections";
    leaf connected {
      type boolean;
      description
        "When set to true, indicates the connection between the
         switch and controller is established.";
    }
  }

  grouping live_ncs_openflow-connections-top {
    description
      "Top-level grouping for OpenFlow controller connections";
    container connections {
      description
        "Enclosing container for list of controller connections";
      list connection {
        key "aux-id";
        description
          "List of connections to the OpenFlow controller.
           The Openflow switch always connects to configured Openflow
           controllers. Each controller can have more than one
           connection, called auxiliary Openflow connections.";
        leaf aux-id {
          type leafref {
            path "../config/aux-id";
          }
          description
            "Reference to auxiliary id list key";
        }
        container config {
          description
            "Configuration data for OpenFlow controller connections";
          uses live_ncs_openflow-connections-config;
        }
        container state {
          description
            "Operational state data for OpenFlow controller
             connections";
          uses live_ncs_openflow-connections-config;
          uses live_ncs_openflow-connections-state;
        }
      }
    }
  }

  grouping live_ncs_openflow-agent-config {
    description
      "Openflow agent config";
    leaf datapath-id {
      type of-types:live_ncs_datapath-id;
      description
        "Datapath unique ID. The lower 48-bits are for
         a MAC address, while the upper 16-bits are
         implementer-defined.";
    }
    leaf failure-mode {
      type of-types:live_ncs_failure-mode;
      description
        "Failure mode for Openflow.";
    }
    leaf backoff-interval {
      type uint32;
      units "seconds";
      description
        "Openflow agent connection backoff interval.";
    }
    leaf max-backoff {
      type uint32;
      units "seconds";
      description
        "Openflow agent max backoff time.";
    }
    leaf inactivity-probe {
      type uint32;
      units "seconds";
      description
        "Openflow agent inactivity probe period.";
    }
  }

  grouping live_ncs_openflow-agent-state {
    description
      "Openflow agent state";
  }

  grouping live_ncs_openflow-agent-top {
    description
      "Top-level for the Openflow agent model";
    container agent {
      description
        "Container for the Openflow agent model.";
      container config {
        description
          "Container for the Openflow agent config.";
        uses live_ncs_openflow-agent-config;
      }
      container state {
        description
          "Container for the Openflow agent state.";
        uses live_ncs_openflow-agent-config;
        uses live_ncs_openflow-agent-state;
      }
    }
  }

  grouping live_ncs_openflow-top {
    description
      "Top-level for the Openflow model";
    container openflow {
      description
        "Container for Openflow model";
      uses live_ncs_openflow-controllers-top;
      uses live_ncs_openflow-agent-top;
    }
  }

  grouping openflow-controller-config {
    description
      "Openflow controller config";
    leaf name {
      type string;
      description
        "Name of this Openflow controller. All connections
         for the same controller need to have the same name.";
    }
  }

  grouping openflow-controller-state {
    description
      "Openflow controller state";
  }

  grouping openflow-controllers-top {
    description
      "Top-level for the Openflow controllers model";
    container controllers {
      description
        "Container for the Openflow controllers model";
      list controller {
        key "name";
        description
          "The Openflow Switch connects to all Openflow controllers
           configured";
        leaf name {
          type leafref {
            path "../config/name";
          }
          description
            "The name identifies the controller.";
        }
        container config {
          description
            "Container for the Openflow controller config.";
          uses openflow-controller-config;
        }
        // NCS drop config false container state
        uses openflow-connections-top;
      }
    }
  }

  grouping openflow-connections-config {
    description
      "Configuration data for OpenFlow controller connections";
    leaf aux-id {
      type of-types:auxiliary-id;
      description
        "Controller auxiliary ID. Must be 0 for the main controller.
         One controller may have multiple auxiliary connections as
         specified by the Openflow protocol. Besides configuring the
         main controller, it is also possible to configure auxiliary
         connections. The main controller must have the aux-id
         set to zero. All others must have an aux-id different
         from 0.";
    }
    leaf priority {
      type uint8;
      description
        "Optional value for servicing auxiliary connections with
         different priorities.";
    }
    leaf address {
      type oc-inet:ip-address;
      description
        "The IP address of the controller.";
    }
    leaf port {
      type oc-inet:port-number;
      default "6653";
      description
        "Controller port to use.";
    }
    leaf transport {
      type of-types:transport;
      default "TCP";
      description
        "Controller transport protocol used.";
    }
    leaf certificate-id {
      type string;
      description
        "Certificate ID is used for TLS connections. When installed,
         certificates are associated with an ID. This ID specifies the
         certificate to use in a TLS connection.";
    }
    leaf source-interface {
      type oc-if:base-interface-ref;
      description
        "Optionally specify the source interface for the
         controller connection.";
    }
  }

  grouping openflow-connections-state {
    description
      "Operational state data for OpenFlow controller connections";
    leaf connected {
      type boolean;
      description
        "When set to true, indicates the connection between the
         switch and controller is established.";
    }
  }

  grouping openflow-connections-top {
    description
      "Top-level grouping for OpenFlow controller connections";
    container connections {
      description
        "Enclosing container for list of controller connections";
      list connection {
        key "aux-id";
        description
          "List of connections to the OpenFlow controller.
           The Openflow switch always connects to configured Openflow
           controllers. Each controller can have more than one
           connection, called auxiliary Openflow connections.";
        leaf aux-id {
          type leafref {
            path "../config/aux-id";
          }
          description
            "Reference to auxiliary id list key";
        }
        container config {
          description
            "Configuration data for OpenFlow controller connections";
          uses openflow-connections-config;
        }
        // NCS drop config false container state
      }
    }
  }

  grouping openflow-agent-config {
    description
      "Openflow agent config";
    leaf datapath-id {
      type of-types:datapath-id;
      description
        "Datapath unique ID. The lower 48-bits are for
         a MAC address, while the upper 16-bits are
         implementer-defined.";
    }
    leaf failure-mode {
      type of-types:failure-mode;
      description
        "Failure mode for Openflow.";
    }
    leaf backoff-interval {
      type uint32;
      units "seconds";
      description
        "Openflow agent connection backoff interval.";
    }
    leaf max-backoff {
      type uint32;
      units "seconds";
      description
        "Openflow agent max backoff time.";
    }
    leaf inactivity-probe {
      type uint32;
      units "seconds";
      description
        "Openflow agent inactivity probe period.";
    }
  }

  grouping openflow-agent-state {
    description
      "Openflow agent state";
  }

  grouping openflow-agent-top {
    description
      "Top-level for the Openflow agent model";
    container agent {
      description
        "Container for the Openflow agent model.";
      container config {
        description
          "Container for the Openflow agent config.";
        uses openflow-agent-config;
      }
      // NCS drop config false container state
    }
  }

  grouping openflow-top {
    description
      "Top-level for the Openflow model";
    container openflow {
      description
        "Container for Openflow model";
      uses openflow-controllers-top;
      uses openflow-agent-top;
    }
  }

  augment "/ncs:compliance/ncs:template/ncs:ned-id/ncs:config/oc-sys:system" {
    description
      "Adding OpenConfig data to the system model";
    uses ncs_compliance_template_openflow-top;
  }
  augment "/ncs:devices/ncs:template/ncs:ned-id/ncs:config/oc-sys:system" {
    description
      "Adding OpenConfig data to the system model";
    uses ncs_template_openflow-top;
  }
  augment "/ncs:devices/ncs:device/ncs:live-status/oc-sys:system" {
    description
      "Adding OpenConfig data to the system model";
    uses live_ncs_openflow-top {
      refine openflow {
        tailf:ncs-device-type "netconf";
        tailf:display-when "not(../../../ncs:module) or ../../../ncs:module[ncs:name='openconfig-openflow'] or (../../../ncs:live-status-protocol[not(ncs:capability)]) or (../../../ncs:live-status-protocol/ncs:capability/ncs:module[.='openconfig-openflow'])";
      }
    }
  }
  augment "/ncs:devices/ncs:device/ncs:config/oc-sys:system" {
    description
      "Adding OpenConfig data to the system model";
    uses openflow-top {
      refine openflow {
        tailf:ncs-device-type "netconf";
        tailf:display-when "not(../../../ncs:module) or ../../../ncs:module[ncs:name='openconfig-openflow']";
      }
    }
  }
}
