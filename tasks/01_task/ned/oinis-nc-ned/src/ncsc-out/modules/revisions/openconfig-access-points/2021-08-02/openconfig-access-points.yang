module openconfig-access-points {
  // Generated by yanger -t ncs
  tailf:mount-id "oinis-nc-ned-nc-1.0:oinis-nc-ned-nc-1.0";
  tailf:ncs-device-type "netconf";

  yang-version 1;
  namespace "http://openconfig.net/yang/wifi/access-points";
  prefix access-points;

  import openconfig-wifi-types {
    prefix oc-wifi-types;
  }
  import openconfig-extensions {
    prefix oc-ext;
  }
  import openconfig-inet-types {
    prefix oc-inet;
  }
  import openconfig-wifi-phy {
    prefix wifi-phy;
  }
  import openconfig-wifi-mac {
    prefix wifi-mac;
  }
  import openconfig-ap-manager {
    prefix ap-manager;
  }
  import openconfig-system {
    prefix oc-sys;
  }
  import tailf-common {
    prefix tailf;
  }
  import tailf-ncs {
    prefix ncs;
  }

  organization
    "OpenConfig working group";
  contact
    "OpenConfig working group
     www.openconfig.net";
  description
    "This module defines the top level WiFi Configurations for a list of
     Access Points.";
  oc-ext:openconfig-version "1.0.0";

  revision 2021-08-02 {
    description
      "Update model version as it is in production.";
    reference "1.0.0";
  }
  revision 2020-04-28 {
    description
      "Change hostname to leaf-ref.";
    reference "0.3.0";
  }
  revision 2018-07-16 {
    description
      "Remove BSSID counters";
    reference "0.2.0";
  }
  revision 2018-02-14 {
    description
      "Initial version";
    reference "0.1.0";
  }

  grouping ncs_compliance_template_assigned-ap-managers-config {
    description
      "AP Manager(s) an AP may join. If cloud manager, this will be
       the cloud instance(s). This is often referred to as 'Controller'.";
    leaf id {
      type string;
      description
        "The unique reference for the AP manager described in the list entry.";
    }
    leaf fqdn {
      type oc-inet:ncs_compliance_template_domain-name;
      description
        "The FQDN of a manager this AP is assigned to. The list should be
         ordered, according to priority. eg Primary first,
         Secondary second, Tertiary third etc.";
    }
    leaf ap-manager-ipv4-address {
      type oc-inet:ncs_compliance_template_ipv4-address;
      description
        "IPv4 address of a manager for this AP. The list should be
         ordered, according to priority. eg. Primary first, Secondary second,
         Tertiary third etc.";
    }
    leaf-list ap-manager-ipv6-address {
      // NCS patched for predictable order
      ordered-by user;
      type oc-inet:ncs_compliance_template_ipv6-address;
      description
        "IPv6 address of a manager for this AP. The list should be
         ordered, according to priority. eg. Primary first, Secondary second,
         Tertiary third etc.";
    }
  }

  grouping ncs_compliance_template_assigned-ap-managers-state {
    description
      "Manager(s) an AP may join. If cloud manager, this will be
       the cloud instance(s).";
    leaf joined {
      type string;
      description
        "True only if this AP is currently joined to a manager. If this AP
         is configured to join manager(s), however is not currently joined
         to any manager, this MUST return False.";
    }
  }

  grouping ncs_compliance_template_manager-ap-parameters-top {
    description
      "Top-level grouping for assigning AP's to manager(s).";
    container assigned-ap-managers {
      description
        "Wireless manager(s) this AP is assigned to. eg. Primary
         Secondary, Tertiary etc.";
      list ap-manager {
        // NCS patched for predictable order
        ordered-by user;
        key "id";
        description
          "Manager(s) this AP is assinged to, referenced by id.";
        leaf id {
          type string;
          description
            "id serves as a reference point to the [1-n] manager(s) this AP
             is assigned to.";
        }
        container config {
          description
            "Config. container for assigning APs to managers.";
          uses ncs_compliance_template_assigned-ap-managers-config;
        }
        // NCS drop config false container state
      }
    }
  }

  grouping ncs_compliance_template_access-points-common-config {
    description
      "Grouping for AP level State data.";
    leaf hostname {
      type string;
      description
        "Access Point FQDN.";
    }
  }

  grouping ncs_compliance_template_access-points-top {
    description
      "Top-level grouping for AP configuration & state data.";
    container access-points {
      description
        "Top most container for configuration and state data for Access
         Points.";
      list access-point {
        // NCS patched for predictable order
        ordered-by user;
        key "hostname";
        description
          "Configuration and state data for the access point referenced in the
           list entry.";
        leaf hostname {
          type string;
          description
            "Access Point FQDN.";
        }
        container config {
          description
            "Config items at the global, Access Point level.";
          uses ncs_compliance_template_access-points-common-config;
        }
        uses wifi-phy:ncs_compliance_template_radio-top;
        uses wifi-mac:ncs_compliance_template_ssid-top;
        uses oc-sys:ncs_compliance_template_system-top;
        uses ncs_compliance_template_manager-ap-parameters-top;
      }
    }
  }

  grouping ncs_template_assigned-ap-managers-config {
    description
      "AP Manager(s) an AP may join. If cloud manager, this will be
       the cloud instance(s). This is often referred to as 'Controller'.";
    leaf id {
      type string;
      description
        "The unique reference for the AP manager described in the list entry.";
    }
    leaf fqdn {
      type oc-inet:ncs_template_domain-name;
      description
        "The FQDN of a manager this AP is assigned to. The list should be
         ordered, according to priority. eg Primary first,
         Secondary second, Tertiary third etc.";
    }
    leaf ap-manager-ipv4-address {
      type oc-inet:ncs_template_ipv4-address;
      description
        "IPv4 address of a manager for this AP. The list should be
         ordered, according to priority. eg. Primary first, Secondary second,
         Tertiary third etc.";
    }
    leaf-list ap-manager-ipv6-address {
      // NCS patched for predictable order
      ordered-by user;
      type oc-inet:ncs_template_ipv6-address;
      description
        "IPv6 address of a manager for this AP. The list should be
         ordered, according to priority. eg. Primary first, Secondary second,
         Tertiary third etc.";
    }
  }

  grouping ncs_template_assigned-ap-managers-state {
    description
      "Manager(s) an AP may join. If cloud manager, this will be
       the cloud instance(s).";
    leaf joined {
      type string;
      description
        "True only if this AP is currently joined to a manager. If this AP
         is configured to join manager(s), however is not currently joined
         to any manager, this MUST return False.";
    }
  }

  grouping ncs_template_manager-ap-parameters-top {
    description
      "Top-level grouping for assigning AP's to manager(s).";
    container assigned-ap-managers {
      description
        "Wireless manager(s) this AP is assigned to. eg. Primary
         Secondary, Tertiary etc.";
      list ap-manager {
        // NCS patched for predictable order
        ordered-by user;
        key "id";
        description
          "Manager(s) this AP is assinged to, referenced by id.";
        leaf id {
          type string;
          description
            "id serves as a reference point to the [1-n] manager(s) this AP
             is assigned to.";
        }
        container config {
          description
            "Config. container for assigning APs to managers.";
          uses ncs_template_assigned-ap-managers-config;
        }
        // NCS drop config false container state
      }
    }
  }

  grouping ncs_template_access-points-common-config {
    description
      "Grouping for AP level State data.";
    leaf hostname {
      type string;
      description
        "Access Point FQDN.";
    }
  }

  grouping ncs_template_access-points-top {
    description
      "Top-level grouping for AP configuration & state data.";
    container access-points {
      description
        "Top most container for configuration and state data for Access
         Points.";
      list access-point {
        // NCS patched for predictable order
        ordered-by user;
        key "hostname";
        description
          "Configuration and state data for the access point referenced in the
           list entry.";
        leaf hostname {
          type string;
          description
            "Access Point FQDN.";
        }
        container config {
          description
            "Config items at the global, Access Point level.";
          uses ncs_template_access-points-common-config;
        }
        uses wifi-phy:ncs_template_radio-top;
        uses wifi-mac:ncs_template_ssid-top;
        uses oc-sys:ncs_template_system-top;
        uses ncs_template_manager-ap-parameters-top;
      }
    }
  }

  grouping ncs_rpc_notif_assigned-ap-managers-config {
    description
      "AP Manager(s) an AP may join. If cloud manager, this will be
       the cloud instance(s). This is often referred to as 'Controller'.";
    leaf id {
      type string;
      description
        "The unique reference for the AP manager described in the list entry.";
    }
    leaf fqdn {
      type oc-inet:ncs_rpc_notif_domain-name;
      description
        "The FQDN of a manager this AP is assigned to. The list should be
         ordered, according to priority. eg Primary first,
         Secondary second, Tertiary third etc.";
    }
    leaf ap-manager-ipv4-address {
      type oc-inet:ncs_rpc_notif_ipv4-address;
      description
        "IPv4 address of a manager for this AP. The list should be
         ordered, according to priority. eg. Primary first, Secondary second,
         Tertiary third etc.";
    }
    leaf-list ap-manager-ipv6-address {
      type oc-inet:ncs_rpc_notif_ipv6-address;
      description
        "IPv6 address of a manager for this AP. The list should be
         ordered, according to priority. eg. Primary first, Secondary second,
         Tertiary third etc.";
    }
  }

  grouping ncs_rpc_notif_assigned-ap-managers-state {
    description
      "Manager(s) an AP may join. If cloud manager, this will be
       the cloud instance(s).";
    leaf joined {
      type boolean;
      description
        "True only if this AP is currently joined to a manager. If this AP
         is configured to join manager(s), however is not currently joined
         to any manager, this MUST return False.";
    }
  }

  grouping ncs_rpc_notif_manager-ap-parameters-top {
    description
      "Top-level grouping for assigning AP's to manager(s).";
    container assigned-ap-managers {
      description
        "Wireless manager(s) this AP is assigned to. eg. Primary
         Secondary, Tertiary etc.";
      list ap-manager {
        key "id";
        description
          "Manager(s) this AP is assinged to, referenced by id.";
        leaf id {
          type leafref {
            path "../config/id";
          }
          description
            "id serves as a reference point to the [1-n] manager(s) this AP
             is assigned to.";
        }
        container config {
          description
            "Config. container for assigning APs to managers.";
          uses ncs_rpc_notif_assigned-ap-managers-config;
        }
        container state {
          config false;
          description
            "State container for APs assigned to managers.";
          uses ncs_rpc_notif_assigned-ap-managers-config;
          uses ncs_rpc_notif_assigned-ap-managers-state;
        }
      }
    }
  }

  grouping ncs_rpc_notif_access-points-common-config {
    description
      "Grouping for AP level State data.";
    leaf hostname {
      type string;
      description
        "Access Point FQDN.";
    }
  }

  grouping ncs_rpc_notif_access-points-top {
    description
      "Top-level grouping for AP configuration & state data.";
    container access-points {
      description
        "Top most container for configuration and state data for Access
         Points.";
      list access-point {
        key "hostname";
        description
          "Configuration and state data for the access point referenced in the
           list entry.";
        leaf hostname {
          type string;
          description
            "Access Point FQDN.";
        }
        container config {
          description
            "Config items at the global, Access Point level.";
          uses ncs_rpc_notif_access-points-common-config;
        }
        uses wifi-phy:ncs_rpc_notif_radio-top;
        uses wifi-mac:ncs_rpc_notif_ssid-top;
        uses oc-sys:ncs_rpc_notif_system-top;
        uses ncs_rpc_notif_manager-ap-parameters-top;
      }
    }
  }

  grouping live_ncs_assigned-ap-managers-config {
    description
      "AP Manager(s) an AP may join. If cloud manager, this will be
       the cloud instance(s). This is often referred to as 'Controller'.";
    leaf id {
      type string;
      description
        "The unique reference for the AP manager described in the list entry.";
    }
    leaf fqdn {
      type oc-inet:live_ncs_domain-name;
      description
        "The FQDN of a manager this AP is assigned to. The list should be
         ordered, according to priority. eg Primary first,
         Secondary second, Tertiary third etc.";
    }
    leaf ap-manager-ipv4-address {
      type oc-inet:live_ncs_ipv4-address;
      description
        "IPv4 address of a manager for this AP. The list should be
         ordered, according to priority. eg. Primary first, Secondary second,
         Tertiary third etc.";
    }
    leaf-list ap-manager-ipv6-address {
      type oc-inet:live_ncs_ipv6-address;
      description
        "IPv6 address of a manager for this AP. The list should be
         ordered, according to priority. eg. Primary first, Secondary second,
         Tertiary third etc.";
    }
  }

  grouping live_ncs_assigned-ap-managers-state {
    description
      "Manager(s) an AP may join. If cloud manager, this will be
       the cloud instance(s).";
    leaf joined {
      type boolean;
      description
        "True only if this AP is currently joined to a manager. If this AP
         is configured to join manager(s), however is not currently joined
         to any manager, this MUST return False.";
    }
  }

  grouping live_ncs_manager-ap-parameters-top {
    description
      "Top-level grouping for assigning AP's to manager(s).";
    container assigned-ap-managers {
      description
        "Wireless manager(s) this AP is assigned to. eg. Primary
         Secondary, Tertiary etc.";
      list ap-manager {
        key "id";
        description
          "Manager(s) this AP is assinged to, referenced by id.";
        leaf id {
          type leafref {
            path "../config/id";
          }
          description
            "id serves as a reference point to the [1-n] manager(s) this AP
             is assigned to.";
        }
        container config {
          description
            "Config. container for assigning APs to managers.";
          uses live_ncs_assigned-ap-managers-config;
        }
        container state {
          description
            "State container for APs assigned to managers.";
          uses live_ncs_assigned-ap-managers-config;
          uses live_ncs_assigned-ap-managers-state;
        }
      }
    }
  }

  grouping live_ncs_access-points-common-config {
    description
      "Grouping for AP level State data.";
    leaf hostname {
      type leafref {
        path "/ncs:devices/ncs:device/ncs:live-status/ap-manager:provision-aps/ap-manager:provision-ap/ap-manager:config/ap-manager:hostname" {
          tailf:xpath-root 3;
        }
      }
      description
        "Access Point FQDN.";
    }
  }

  grouping live_ncs_access-points-top {
    description
      "Top-level grouping for AP configuration & state data.";
    container access-points {
      description
        "Top most container for configuration and state data for Access
         Points.";
      list access-point {
        key "hostname";
        description
          "Configuration and state data for the access point referenced in the
           list entry.";
        leaf hostname {
          type leafref {
            path "../config/hostname";
          }
          description
            "Access Point FQDN.";
        }
        container config {
          description
            "Config items at the global, Access Point level.";
          uses live_ncs_access-points-common-config;
        }
        uses wifi-phy:live_ncs_radio-top;
        uses wifi-mac:live_ncs_ssid-top;
        uses oc-sys:live_ncs_system-top;
        uses live_ncs_manager-ap-parameters-top;
      }
    }
  }

  grouping assigned-ap-managers-config {
    description
      "AP Manager(s) an AP may join. If cloud manager, this will be
       the cloud instance(s). This is often referred to as 'Controller'.";
    leaf id {
      type string;
      description
        "The unique reference for the AP manager described in the list entry.";
    }
    leaf fqdn {
      type oc-inet:domain-name;
      description
        "The FQDN of a manager this AP is assigned to. The list should be
         ordered, according to priority. eg Primary first,
         Secondary second, Tertiary third etc.";
    }
    leaf ap-manager-ipv4-address {
      type oc-inet:ipv4-address;
      description
        "IPv4 address of a manager for this AP. The list should be
         ordered, according to priority. eg. Primary first, Secondary second,
         Tertiary third etc.";
    }
    leaf-list ap-manager-ipv6-address {
      type oc-inet:ipv6-address;
      description
        "IPv6 address of a manager for this AP. The list should be
         ordered, according to priority. eg. Primary first, Secondary second,
         Tertiary third etc.";
    }
  }

  grouping assigned-ap-managers-state {
    description
      "Manager(s) an AP may join. If cloud manager, this will be
       the cloud instance(s).";
    leaf joined {
      type boolean;
      description
        "True only if this AP is currently joined to a manager. If this AP
         is configured to join manager(s), however is not currently joined
         to any manager, this MUST return False.";
    }
  }

  grouping manager-ap-parameters-top {
    description
      "Top-level grouping for assigning AP's to manager(s).";
    container assigned-ap-managers {
      description
        "Wireless manager(s) this AP is assigned to. eg. Primary
         Secondary, Tertiary etc.";
      list ap-manager {
        key "id";
        description
          "Manager(s) this AP is assinged to, referenced by id.";
        leaf id {
          type leafref {
            path "../config/id";
          }
          description
            "id serves as a reference point to the [1-n] manager(s) this AP
             is assigned to.";
        }
        container config {
          description
            "Config. container for assigning APs to managers.";
          uses assigned-ap-managers-config;
        }
        // NCS drop config false container state
      }
    }
  }

  grouping access-points-common-config {
    description
      "Grouping for AP level State data.";
    leaf hostname {
      type leafref {
        path "/ncs:devices/ncs:device/ncs:config/ap-manager:provision-aps/ap-manager:provision-ap/ap-manager:config/ap-manager:hostname" {
          tailf:xpath-root 3;
        }
      }
      description
        "Access Point FQDN.";
    }
  }

  grouping access-points-top {
    description
      "Top-level grouping for AP configuration & state data.";
    container access-points {
      description
        "Top most container for configuration and state data for Access
         Points.";
      list access-point {
        key "hostname";
        description
          "Configuration and state data for the access point referenced in the
           list entry.";
        leaf hostname {
          type leafref {
            path "../config/hostname";
          }
          description
            "Access Point FQDN.";
        }
        container config {
          description
            "Config items at the global, Access Point level.";
          uses access-points-common-config;
        }
        uses wifi-phy:radio-top;
        uses wifi-mac:ssid-top;
        uses oc-sys:system-top;
        uses manager-ap-parameters-top;
      }
    }
  }

  augment "/ncs:devices/ncs:device/ncs:config" {
    uses access-points-top {
      refine access-points {
        tailf:ncs-device-type "netconf";
        tailf:display-when "not(../../ncs:module) or ../../ncs:module[ncs:name='openconfig-access-points']";
      }
    }
  }
  augment "/ncs:devices/ncs:device/ncs:live-status" {
    uses live_ncs_access-points-top {
      refine access-points {
        tailf:ncs-device-type "netconf";
        tailf:display-when "not(../../ncs:module) or ../../ncs:module[ncs:name='openconfig-access-points'] or (../../ncs:live-status-protocol[not(ncs:capability)]) or (../../ncs:live-status-protocol/ncs:capability/ncs:module[.='openconfig-access-points'])";
      }
    }
  }
  augment "/ncs:devices/ncs:template/ncs:ned-id/ncs:config" {
    uses ncs_template_access-points-top;
  }
  augment "/ncs:compliance/ncs:template/ncs:ned-id/ncs:config" {
    uses ncs_compliance_template_access-points-top;
  }
  deviation "/ncs:compliance/ncs:template/ncs:ned-id/ncs:config/oc-sys:system/oc-sys:config/oc-sys:hostname" {
    deviate not-supported;
  }
  deviation "/ncs:devices/ncs:template/ncs:ned-id/ncs:config/oc-sys:system/oc-sys:config/oc-sys:hostname" {
    deviate not-supported;
  }
  deviation "/ncs:devices/ncs:device/ncs:live-status/oc-sys:system/oc-sys:config/oc-sys:hostname" {
    deviate not-supported;
  }
  deviation "/ncs:devices/ncs:device/ncs:config/oc-sys:system/oc-sys:config/oc-sys:hostname" {
    deviate not-supported;
  }
  deviation "/ncs:devices/ncs:device/ncs:live-status/oc-sys:system/oc-sys:state/oc-sys:hostname" {
    deviate not-supported;
  }
}
