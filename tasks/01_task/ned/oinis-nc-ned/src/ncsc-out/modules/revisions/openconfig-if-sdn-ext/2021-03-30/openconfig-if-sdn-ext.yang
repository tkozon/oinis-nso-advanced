module openconfig-if-sdn-ext {
  // Generated by yanger -t ncs
  tailf:mount-id "oinis-nc-ned-nc-1.0:oinis-nc-ned-nc-1.0";
  tailf:ncs-device-type "netconf";

  yang-version 1;
  namespace "http://openconfig.net/interfaces/sdn-ext";
  prefix oc-if-sdn;

  import openconfig-extensions {
    prefix oc-ext;
  }
  import openconfig-interfaces {
    prefix oc-if;
  }
  import tailf-common {
    prefix tailf;
  }
  import tailf-ncs {
    prefix ncs;
  }

  organization
    "OpenConfig working group";
  contact
    "www.openconfig.net";
  description
    "This module provides extensions to the OpenConfig interfaces
     module for network elements that support external 'SDN' control
     of their interfaces.";
  oc-ext:catalog-organization "openconfig";
  oc-ext:origin "openconfig";
  oc-ext:openconfig-version "0.1.0";

  revision 2021-03-30 {
    description
      "Initial revision.";
    reference "0.1.0";
  }

  grouping ncs_compliance_template_sdn-interface-config {
    description
      "Configuration parameters applicable to interfaces on devices
       that support SDN control.";
    leaf forwarding-viable {
      type string;
      // NCS drop default statement
      description
        "This value indicates whether the interface may be used
         to route traffic or not.  If set to false, the
         interface is not used for forwarding traffic, but as long as
         it is up, the interface still maintains its layer-2
         adjacencies and runs its configured layer-2 functions
         (e.g., LLDP, etc.).
         This is used by an external programming entity to disable an interface
         (usually part of an aggregate) for the purposes of forwarding
         traffic. This allows a logical aggregate to continue to be
         used with partial capacity, for example.  Note that setting
         `forwarding-viable = false` is not equivalent to
         administratively disabling the interface -- in particular, the
         interface is expected to participate in L2 protocols such as
         LLDP or LACP even if it blocked from forwarding traffic.";
    }
  }

  grouping ncs_template_sdn-interface-config {
    description
      "Configuration parameters applicable to interfaces on devices
       that support SDN control.";
    leaf forwarding-viable {
      type string;
      // NCS drop default statement
      description
        "This value indicates whether the interface may be used
         to route traffic or not.  If set to false, the
         interface is not used for forwarding traffic, but as long as
         it is up, the interface still maintains its layer-2
         adjacencies and runs its configured layer-2 functions
         (e.g., LLDP, etc.).
         This is used by an external programming entity to disable an interface
         (usually part of an aggregate) for the purposes of forwarding
         traffic. This allows a logical aggregate to continue to be
         used with partial capacity, for example.  Note that setting
         `forwarding-viable = false` is not equivalent to
         administratively disabling the interface -- in particular, the
         interface is expected to participate in L2 protocols such as
         LLDP or LACP even if it blocked from forwarding traffic.";
    }
  }

  grouping ncs_rpc_notif_sdn-interface-config {
    description
      "Configuration parameters applicable to interfaces on devices
       that support SDN control.";
    leaf forwarding-viable {
      type boolean;
      default "true";
      description
        "This value indicates whether the interface may be used
         to route traffic or not.  If set to false, the
         interface is not used for forwarding traffic, but as long as
         it is up, the interface still maintains its layer-2
         adjacencies and runs its configured layer-2 functions
         (e.g., LLDP, etc.).
         This is used by an external programming entity to disable an interface
         (usually part of an aggregate) for the purposes of forwarding
         traffic. This allows a logical aggregate to continue to be
         used with partial capacity, for example.  Note that setting
         `forwarding-viable = false` is not equivalent to
         administratively disabling the interface -- in particular, the
         interface is expected to participate in L2 protocols such as
         LLDP or LACP even if it blocked from forwarding traffic.";
    }
  }

  grouping live_ncs_sdn-interface-config {
    description
      "Configuration parameters applicable to interfaces on devices
       that support SDN control.";
    leaf forwarding-viable {
      type boolean;
      // NCS drop default statement
      description
        "This value indicates whether the interface may be used
         to route traffic or not.  If set to false, the
         interface is not used for forwarding traffic, but as long as
         it is up, the interface still maintains its layer-2
         adjacencies and runs its configured layer-2 functions
         (e.g., LLDP, etc.).
         This is used by an external programming entity to disable an interface
         (usually part of an aggregate) for the purposes of forwarding
         traffic. This allows a logical aggregate to continue to be
         used with partial capacity, for example.  Note that setting
         `forwarding-viable = false` is not equivalent to
         administratively disabling the interface -- in particular, the
         interface is expected to participate in L2 protocols such as
         LLDP or LACP even if it blocked from forwarding traffic.";
    }
  }

  grouping sdn-interface-config {
    description
      "Configuration parameters applicable to interfaces on devices
       that support SDN control.";
    leaf forwarding-viable {
      type boolean;
      default "true";
      description
        "This value indicates whether the interface may be used
         to route traffic or not.  If set to false, the
         interface is not used for forwarding traffic, but as long as
         it is up, the interface still maintains its layer-2
         adjacencies and runs its configured layer-2 functions
         (e.g., LLDP, etc.).
         This is used by an external programming entity to disable an interface
         (usually part of an aggregate) for the purposes of forwarding
         traffic. This allows a logical aggregate to continue to be
         used with partial capacity, for example.  Note that setting
         `forwarding-viable = false` is not equivalent to
         administratively disabling the interface -- in particular, the
         interface is expected to participate in L2 protocols such as
         LLDP or LACP even if it blocked from forwarding traffic.";
    }
  }

  augment "/ncs:compliance/ncs:template/ncs:ned-id/ncs:config/oc-if:interfaces/oc-if:interface/oc-if:config" {
    description
      "Add SDN extensions to interface intended configuration.";
    uses ncs_compliance_template_sdn-interface-config;
  }
  augment "/ncs:devices/ncs:template/ncs:ned-id/ncs:config/oc-if:interfaces/oc-if:interface/oc-if:config" {
    description
      "Add SDN extensions to interface intended configuration.";
    uses ncs_template_sdn-interface-config;
  }
  augment "/ncs:devices/ncs:device/ncs:live-status/oc-if:interfaces/oc-if:interface/oc-if:config" {
    description
      "Add SDN extensions to interface intended configuration.";
    uses live_ncs_sdn-interface-config {
      refine forwarding-viable {
        tailf:ncs-device-type "netconf";
        tailf:display-when "not(../../../../../ncs:module) or ../../../../../ncs:module[ncs:name='openconfig-if-sdn-ext'] or (../../../../../ncs:live-status-protocol[not(ncs:capability)]) or (../../../../../ncs:live-status-protocol/ncs:capability/ncs:module[.='openconfig-if-sdn-ext'])";
      }
    }
  }
  augment "/ncs:devices/ncs:device/ncs:config/oc-if:interfaces/oc-if:interface/oc-if:config" {
    description
      "Add SDN extensions to interface intended configuration.";
    uses sdn-interface-config {
      refine forwarding-viable {
        tailf:ncs-device-type "netconf";
        tailf:display-when "not(../../../../../ncs:module) or ../../../../../ncs:module[ncs:name='openconfig-if-sdn-ext']";
      }
    }
  }
  augment "/ncs:devices/ncs:device/ncs:live-status/oc-if:interfaces/oc-if:interface/oc-if:state" {
    description
      "Add SDN extensions to interface applied configuration.";
    uses live_ncs_sdn-interface-config {
      refine forwarding-viable {
        tailf:ncs-device-type "netconf";
        tailf:display-when "not(../../../../../ncs:module) or ../../../../../ncs:module[ncs:name='openconfig-if-sdn-ext'] or (../../../../../ncs:live-status-protocol[not(ncs:capability)]) or (../../../../../ncs:live-status-protocol/ncs:capability/ncs:module[.='openconfig-if-sdn-ext'])";
      }
    }
  }
}
