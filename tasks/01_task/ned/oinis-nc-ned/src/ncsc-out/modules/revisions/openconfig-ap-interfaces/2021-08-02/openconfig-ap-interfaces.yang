module openconfig-ap-interfaces {
  // Generated by yanger -t ncs
  tailf:mount-id "oinis-nc-ned-nc-1.0:oinis-nc-ned-nc-1.0";
  tailf:ncs-device-type "netconf";

  yang-version 1;
  namespace "http://openconfig.net/yang/ap-interfaces";
  prefix oc-ap-if;

  import openconfig-extensions {
    prefix oc-ext;
  }
  import openconfig-interfaces {
    prefix oc-if;
  }
  import openconfig-access-points {
    prefix oc-access-points;
  }
  import openconfig-if-ethernet {
    prefix oc-eth;
  }
  import openconfig-if-aggregate {
    prefix oc-lag;
  }
  import openconfig-if-poe {
    prefix oc-poe;
  }
  import openconfig-vlan {
    prefix oc-vlan;
  }
  import openconfig-if-tunnel {
    prefix oc-tun;
  }
  import openconfig-if-ip {
    prefix oc-ip;
  }
  import openconfig-if-8021x {
    prefix oc-1x;
  }
  import tailf-common {
    prefix tailf;
  }
  import tailf-ncs {
    prefix ncs;
  }

  organization
    "OpenConfig working group";
  contact
    "OpenConfig working group
     www.openconfig.net";
  description
    "This module defines the configuration and state data for
     non-radio interfaces on WiFi Access Points.";
  oc-ext:openconfig-version "1.0.0";

  revision 2021-08-02 {
    description
      "Update model version as it is in production.";
    reference "1.0.0";
  }
  revision 2020-03-24 {
    description
      "Update namespace based on new directory structure";
    reference "0.1.1";
  }
  revision 2019-05-29 {
    description
      "Initial version.";
    reference "0.1.0";
  }

  grouping ncs_compliance_template_ap-interfaces-top {
    description
      "Top-level grouping for AP interface configuration and
       operational state data";
    container interfaces {
      description
        "Top level container for non-radio AP interfaces, including
         configuration and state data.";
      list interface {
        // NCS patched for predictable order
        ordered-by user;
        key "name";
        description
          "The list of named interfaces on the device.";
        leaf name {
          type string;
          description
            "References the name of the interface";
        }
        container config {
          description
            "Configurable items at the global, physical interface
             level";
          oc-ext:telemetry-on-change;
          uses oc-if:ncs_compliance_template_interface-phys-config;
        }
        // NCS drop config false container state
      }
    }
  }

  grouping ncs_template_ap-interfaces-top {
    description
      "Top-level grouping for AP interface configuration and
       operational state data";
    container interfaces {
      description
        "Top level container for non-radio AP interfaces, including
         configuration and state data.";
      list interface {
        // NCS patched for predictable order
        ordered-by user;
        key "name";
        description
          "The list of named interfaces on the device.";
        leaf name {
          type string;
          description
            "References the name of the interface";
        }
        container config {
          description
            "Configurable items at the global, physical interface
             level";
          oc-ext:telemetry-on-change;
          uses oc-if:ncs_template_interface-phys-config;
        }
        // NCS drop config false container state
      }
    }
  }

  grouping ncs_rpc_notif_ap-interfaces-top {
    description
      "Top-level grouping for AP interface configuration and
       operational state data";
    container interfaces {
      description
        "Top level container for non-radio AP interfaces, including
         configuration and state data.";
      list interface {
        key "name";
        description
          "The list of named interfaces on the device.";
        leaf name {
          type leafref {
            path "../config/name";
          }
          description
            "References the name of the interface";
        }
        container config {
          description
            "Configurable items at the global, physical interface
             level";
          oc-ext:telemetry-on-change;
          uses oc-if:ncs_rpc_notif_interface-phys-config;
        }
        container state {
          config false;
          description
            "Operational state data at the global interface level";
          uses oc-if:ncs_rpc_notif_interface-phys-config;
          uses oc-if:ncs_rpc_notif_interface-common-state;
          uses oc-if:ncs_rpc_notif_interface-counters-state;
        }
      }
    }
  }

  grouping live_ncs_ap-interfaces-top {
    description
      "Top-level grouping for AP interface configuration and
       operational state data";
    container interfaces {
      description
        "Top level container for non-radio AP interfaces, including
         configuration and state data.";
      list interface {
        key "name";
        description
          "The list of named interfaces on the device.";
        leaf name {
          type leafref {
            path "../config/name";
          }
          description
            "References the name of the interface";
        }
        container config {
          description
            "Configurable items at the global, physical interface
             level";
          oc-ext:telemetry-on-change;
          uses oc-if:live_ncs_interface-phys-config;
        }
        container state {
          description
            "Operational state data at the global interface level";
          uses oc-if:live_ncs_interface-phys-config;
          uses oc-if:live_ncs_interface-common-state;
          uses oc-if:live_ncs_interface-counters-state;
        }
      }
    }
  }

  grouping ap-interfaces-top {
    description
      "Top-level grouping for AP interface configuration and
       operational state data";
    container interfaces {
      description
        "Top level container for non-radio AP interfaces, including
         configuration and state data.";
      list interface {
        key "name";
        description
          "The list of named interfaces on the device.";
        leaf name {
          type leafref {
            path "../config/name";
          }
          description
            "References the name of the interface";
        }
        container config {
          description
            "Configurable items at the global, physical interface
             level";
          oc-ext:telemetry-on-change;
          uses oc-if:interface-phys-config;
        }
        // NCS drop config false container state
      }
    }
  }

  augment "/ncs:compliance/ncs:template/ncs:ned-id/ncs:config/oc-access-points:access-points/oc-access-points:access-point" {
    description
      "Adds interface configuration and state to access-points model";
    uses ncs_compliance_template_ap-interfaces-top;
  }
  augment "/ncs:devices/ncs:template/ncs:ned-id/ncs:config/oc-access-points:access-points/oc-access-points:access-point" {
    description
      "Adds interface configuration and state to access-points model";
    uses ncs_template_ap-interfaces-top;
  }
  augment "/ncs:devices/ncs:device/ncs:live-status/oc-access-points:access-points/oc-access-points:access-point" {
    description
      "Adds interface configuration and state to access-points model";
    uses live_ncs_ap-interfaces-top {
      refine interfaces {
        tailf:ncs-device-type "netconf";
        tailf:display-when "not(../../../../ncs:module) or ../../../../ncs:module[ncs:name='openconfig-ap-interfaces'] or (../../../../ncs:live-status-protocol[not(ncs:capability)]) or (../../../../ncs:live-status-protocol/ncs:capability/ncs:module[.='openconfig-ap-interfaces'])";
      }
    }
  }
  augment "/ncs:devices/ncs:device/ncs:config/oc-access-points:access-points/oc-access-points:access-point" {
    description
      "Adds interface configuration and state to access-points model";
    uses ap-interfaces-top {
      refine interfaces {
        tailf:ncs-device-type "netconf";
        tailf:display-when "not(../../../../ncs:module) or ../../../../ncs:module[ncs:name='openconfig-ap-interfaces']";
      }
    }
  }
  augment "/ncs:compliance/ncs:template/ncs:ned-id/ncs:config/oc-access-points:access-points/oc-access-points:access-point/oc-ap-if:interfaces/oc-ap-if:interface" {
    description
      "Adds ethernet interface configuration and state to
       access-points model";
    uses oc-eth:ncs_compliance_template_ethernet-top;
  }
  augment "/ncs:devices/ncs:template/ncs:ned-id/ncs:config/oc-access-points:access-points/oc-access-points:access-point/oc-ap-if:interfaces/oc-ap-if:interface" {
    description
      "Adds ethernet interface configuration and state to
       access-points model";
    uses oc-eth:ncs_template_ethernet-top;
  }
  augment "/ncs:devices/ncs:device/ncs:live-status/oc-access-points:access-points/oc-access-points:access-point/oc-ap-if:interfaces/oc-ap-if:interface" {
    description
      "Adds ethernet interface configuration and state to
       access-points model";
    uses oc-eth:live_ncs_ethernet-top {
      refine ethernet {
        tailf:ncs-device-type "netconf";
        tailf:display-when "not(../../../../../../ncs:module) or ../../../../../../ncs:module[ncs:name='openconfig-ap-interfaces'] or (../../../../../../ncs:live-status-protocol[not(ncs:capability)]) or (../../../../../../ncs:live-status-protocol/ncs:capability/ncs:module[.='openconfig-ap-interfaces'])";
      }
    }
  }
  augment "/ncs:devices/ncs:device/ncs:config/oc-access-points:access-points/oc-access-points:access-point/oc-ap-if:interfaces/oc-ap-if:interface" {
    description
      "Adds ethernet interface configuration and state to
       access-points model";
    uses oc-eth:ethernet-top {
      refine ethernet {
        tailf:ncs-device-type "netconf";
        tailf:display-when "not(../../../../../../ncs:module) or ../../../../../../ncs:module[ncs:name='openconfig-ap-interfaces']";
      }
    }
  }
  augment "/ncs:compliance/ncs:template/ncs:ned-id/ncs:config/oc-access-points:access-points/oc-access-points:access-point/oc-ap-if:interfaces/oc-ap-if:interface/oc-ap-if:ethernet" {
    description
      "Adds 802.1X settings to individual Ethernet interfaces";
    uses oc-1x:ncs_compliance_template_dot1x-top;
  }
  augment "/ncs:devices/ncs:template/ncs:ned-id/ncs:config/oc-access-points:access-points/oc-access-points:access-point/oc-ap-if:interfaces/oc-ap-if:interface/oc-ap-if:ethernet" {
    description
      "Adds 802.1X settings to individual Ethernet interfaces";
    uses oc-1x:ncs_template_dot1x-top;
  }
  augment "/ncs:devices/ncs:device/ncs:live-status/oc-access-points:access-points/oc-access-points:access-point/oc-ap-if:interfaces/oc-ap-if:interface/oc-ap-if:ethernet" {
    description
      "Adds 802.1X settings to individual Ethernet interfaces";
    uses oc-1x:live_ncs_dot1x-top {
      refine authenticated-sessions {
        tailf:ncs-device-type "netconf";
        tailf:display-when "not(../../../../../../../ncs:module) or ../../../../../../../ncs:module[ncs:name='openconfig-ap-interfaces'] or (../../../../../../../ncs:live-status-protocol[not(ncs:capability)]) or (../../../../../../../ncs:live-status-protocol/ncs:capability/ncs:module[.='openconfig-ap-interfaces'])";
      }
      refine dot1x {
        tailf:ncs-device-type "netconf";
        tailf:display-when "not(../../../../../../../ncs:module) or ../../../../../../../ncs:module[ncs:name='openconfig-ap-interfaces'] or (../../../../../../../ncs:live-status-protocol[not(ncs:capability)]) or (../../../../../../../ncs:live-status-protocol/ncs:capability/ncs:module[.='openconfig-ap-interfaces'])";
      }
    }
  }
  augment "/ncs:devices/ncs:device/ncs:config/oc-access-points:access-points/oc-access-points:access-point/oc-ap-if:interfaces/oc-ap-if:interface/oc-ap-if:ethernet" {
    description
      "Adds 802.1X settings to individual Ethernet interfaces";
    uses oc-1x:dot1x-top {
      refine authenticated-sessions {
        tailf:ncs-device-type "netconf";
        tailf:display-when "not(../../../../../../../ncs:module) or ../../../../../../../ncs:module[ncs:name='openconfig-ap-interfaces']";
      }
      refine dot1x {
        tailf:ncs-device-type "netconf";
        tailf:display-when "not(../../../../../../../ncs:module) or ../../../../../../../ncs:module[ncs:name='openconfig-ap-interfaces']";
      }
    }
  }
  augment "/ncs:compliance/ncs:template/ncs:ned-id/ncs:config/oc-access-points:access-points/oc-access-points:access-point/oc-ap-if:interfaces/oc-ap-if:interface/oc-ap-if:ethernet/oc-ap-if:switched-vlan" {
    description
      "Adds vlan-map to switched-vlans.";
    uses oc-1x:ncs_compliance_template_vlan-map-top;
  }
  augment "/ncs:devices/ncs:template/ncs:ned-id/ncs:config/oc-access-points:access-points/oc-access-points:access-point/oc-ap-if:interfaces/oc-ap-if:interface/oc-ap-if:ethernet/oc-ap-if:switched-vlan" {
    description
      "Adds vlan-map to switched-vlans.";
    uses oc-1x:ncs_template_vlan-map-top;
  }
  augment "/ncs:devices/ncs:device/ncs:live-status/oc-access-points:access-points/oc-access-points:access-point/oc-ap-if:interfaces/oc-ap-if:interface/oc-ap-if:ethernet/oc-ap-if:switched-vlan" {
    description
      "Adds vlan-map to switched-vlans.";
    uses oc-1x:live_ncs_vlan-map-top {
      refine dot1x-vlan-map {
        tailf:ncs-device-type "netconf";
        tailf:display-when "not(../../../../../../../../ncs:module) or ../../../../../../../../ncs:module[ncs:name='openconfig-ap-interfaces'] or (../../../../../../../../ncs:live-status-protocol[not(ncs:capability)]) or (../../../../../../../../ncs:live-status-protocol/ncs:capability/ncs:module[.='openconfig-ap-interfaces'])";
      }
    }
  }
  augment "/ncs:devices/ncs:device/ncs:config/oc-access-points:access-points/oc-access-points:access-point/oc-ap-if:interfaces/oc-ap-if:interface/oc-ap-if:ethernet/oc-ap-if:switched-vlan" {
    description
      "Adds vlan-map to switched-vlans.";
    uses oc-1x:vlan-map-top {
      refine dot1x-vlan-map {
        tailf:ncs-device-type "netconf";
        tailf:display-when "not(../../../../../../../../ncs:module) or ../../../../../../../../ncs:module[ncs:name='openconfig-ap-interfaces']";
      }
    }
  }
  augment "/ncs:compliance/ncs:template/ncs:ned-id/ncs:config/oc-access-points:access-points/oc-access-points:access-point/oc-ap-if:interfaces/oc-ap-if:interface" {
    description
      "Adds subinterface configuration and state to
       access-points model";
    uses oc-if:ncs_compliance_template_subinterfaces-top;
  }
  augment "/ncs:devices/ncs:template/ncs:ned-id/ncs:config/oc-access-points:access-points/oc-access-points:access-point/oc-ap-if:interfaces/oc-ap-if:interface" {
    description
      "Adds subinterface configuration and state to
       access-points model";
    uses oc-if:ncs_template_subinterfaces-top;
  }
  augment "/ncs:devices/ncs:device/ncs:live-status/oc-access-points:access-points/oc-access-points:access-point/oc-ap-if:interfaces/oc-ap-if:interface" {
    description
      "Adds subinterface configuration and state to
       access-points model";
    uses oc-if:live_ncs_subinterfaces-top {
      refine subinterfaces {
        tailf:ncs-device-type "netconf";
        tailf:display-when "not(../../../../../../ncs:module) or ../../../../../../ncs:module[ncs:name='openconfig-ap-interfaces'] or (../../../../../../ncs:live-status-protocol[not(ncs:capability)]) or (../../../../../../ncs:live-status-protocol/ncs:capability/ncs:module[.='openconfig-ap-interfaces'])";
      }
    }
  }
  augment "/ncs:devices/ncs:device/ncs:config/oc-access-points:access-points/oc-access-points:access-point/oc-ap-if:interfaces/oc-ap-if:interface" {
    description
      "Adds subinterface configuration and state to
       access-points model";
    uses oc-if:subinterfaces-top {
      refine subinterfaces {
        tailf:ncs-device-type "netconf";
        tailf:display-when "not(../../../../../../ncs:module) or ../../../../../../ncs:module[ncs:name='openconfig-ap-interfaces']";
      }
    }
  }
  augment "/ncs:compliance/ncs:template/ncs:ned-id/ncs:config/oc-access-points:access-points/oc-access-points:access-point/oc-ap-if:interfaces/oc-ap-if:interface/oc-ap-if:subinterfaces/oc-ap-if:subinterface" {
    description
      "IPv4 address family configuration for
       interfaces";
    uses oc-ip:ncs_compliance_template_ipv4-top;
  }
  augment "/ncs:devices/ncs:template/ncs:ned-id/ncs:config/oc-access-points:access-points/oc-access-points:access-point/oc-ap-if:interfaces/oc-ap-if:interface/oc-ap-if:subinterfaces/oc-ap-if:subinterface" {
    description
      "IPv4 address family configuration for
       interfaces";
    uses oc-ip:ncs_template_ipv4-top;
  }
  augment "/ncs:devices/ncs:device/ncs:live-status/oc-access-points:access-points/oc-access-points:access-point/oc-ap-if:interfaces/oc-ap-if:interface/oc-ap-if:subinterfaces/oc-ap-if:subinterface" {
    description
      "IPv4 address family configuration for
       interfaces";
    uses oc-ip:live_ncs_ipv4-top {
      refine ipv4 {
        tailf:ncs-device-type "netconf";
        tailf:display-when "not(../../../../../../../../ncs:module) or ../../../../../../../../ncs:module[ncs:name='openconfig-ap-interfaces'] or (../../../../../../../../ncs:live-status-protocol[not(ncs:capability)]) or (../../../../../../../../ncs:live-status-protocol/ncs:capability/ncs:module[.='openconfig-ap-interfaces'])";
      }
    }
  }
  augment "/ncs:devices/ncs:device/ncs:config/oc-access-points:access-points/oc-access-points:access-point/oc-ap-if:interfaces/oc-ap-if:interface/oc-ap-if:subinterfaces/oc-ap-if:subinterface" {
    description
      "IPv4 address family configuration for
       interfaces";
    uses oc-ip:ipv4-top {
      refine ipv4 {
        tailf:ncs-device-type "netconf";
        tailf:display-when "not(../../../../../../../../ncs:module) or ../../../../../../../../ncs:module[ncs:name='openconfig-ap-interfaces']";
      }
    }
  }
  augment "/ncs:compliance/ncs:template/ncs:ned-id/ncs:config/oc-access-points:access-points/oc-access-points:access-point/oc-ap-if:interfaces/oc-ap-if:interface/oc-ap-if:subinterfaces/oc-ap-if:subinterface" {
    description
      "IPv6 address family configuration for
       interfaces";
    uses oc-ip:ncs_compliance_template_ipv6-top;
  }
  augment "/ncs:devices/ncs:template/ncs:ned-id/ncs:config/oc-access-points:access-points/oc-access-points:access-point/oc-ap-if:interfaces/oc-ap-if:interface/oc-ap-if:subinterfaces/oc-ap-if:subinterface" {
    description
      "IPv6 address family configuration for
       interfaces";
    uses oc-ip:ncs_template_ipv6-top;
  }
  augment "/ncs:devices/ncs:device/ncs:live-status/oc-access-points:access-points/oc-access-points:access-point/oc-ap-if:interfaces/oc-ap-if:interface/oc-ap-if:subinterfaces/oc-ap-if:subinterface" {
    description
      "IPv6 address family configuration for
       interfaces";
    uses oc-ip:live_ncs_ipv6-top {
      refine ipv6 {
        tailf:ncs-device-type "netconf";
        tailf:display-when "not(../../../../../../../../ncs:module) or ../../../../../../../../ncs:module[ncs:name='openconfig-ap-interfaces'] or (../../../../../../../../ncs:live-status-protocol[not(ncs:capability)]) or (../../../../../../../../ncs:live-status-protocol/ncs:capability/ncs:module[.='openconfig-ap-interfaces'])";
      }
    }
  }
  augment "/ncs:devices/ncs:device/ncs:config/oc-access-points:access-points/oc-access-points:access-point/oc-ap-if:interfaces/oc-ap-if:interface/oc-ap-if:subinterfaces/oc-ap-if:subinterface" {
    description
      "IPv6 address family configuration for
       interfaces";
    uses oc-ip:ipv6-top {
      refine ipv6 {
        tailf:ncs-device-type "netconf";
        tailf:display-when "not(../../../../../../../../ncs:module) or ../../../../../../../../ncs:module[ncs:name='openconfig-ap-interfaces']";
      }
    }
  }
  augment "/ncs:compliance/ncs:template/ncs:ned-id/ncs:config/oc-access-points:access-points/oc-access-points:access-point/oc-ap-if:interfaces/oc-ap-if:interface" {
    description
      "Adds lag configuration and state to access-points model";
    uses oc-lag:ncs_compliance_template_aggregation-logical-top;
  }
  augment "/ncs:devices/ncs:template/ncs:ned-id/ncs:config/oc-access-points:access-points/oc-access-points:access-point/oc-ap-if:interfaces/oc-ap-if:interface" {
    description
      "Adds lag configuration and state to access-points model";
    uses oc-lag:ncs_template_aggregation-logical-top;
  }
  augment "/ncs:devices/ncs:device/ncs:live-status/oc-access-points:access-points/oc-access-points:access-point/oc-ap-if:interfaces/oc-ap-if:interface" {
    description
      "Adds lag configuration and state to access-points model";
    uses oc-lag:live_ncs_aggregation-logical-top {
      refine aggregation {
        tailf:ncs-device-type "netconf";
        tailf:display-when "not(../../../../../../ncs:module) or ../../../../../../ncs:module[ncs:name='openconfig-ap-interfaces'] or (../../../../../../ncs:live-status-protocol[not(ncs:capability)]) or (../../../../../../ncs:live-status-protocol/ncs:capability/ncs:module[.='openconfig-ap-interfaces'])";
      }
    }
  }
  augment "/ncs:devices/ncs:device/ncs:config/oc-access-points:access-points/oc-access-points:access-point/oc-ap-if:interfaces/oc-ap-if:interface" {
    description
      "Adds lag configuration and state to access-points model";
    uses oc-lag:aggregation-logical-top {
      refine aggregation {
        tailf:ncs-device-type "netconf";
        tailf:display-when "not(../../../../../../ncs:module) or ../../../../../../ncs:module[ncs:name='openconfig-ap-interfaces']";
      }
    }
  }
  augment "/ncs:compliance/ncs:template/ncs:ned-id/ncs:config/oc-access-points:access-points/oc-access-points:access-point/oc-ap-if:interfaces/oc-ap-if:interface/oc-ap-if:ethernet" {
    description
      "Adds poe configuration and state to access-points model";
    uses oc-poe:ncs_compliance_template_poe-ethernet-top;
  }
  augment "/ncs:devices/ncs:template/ncs:ned-id/ncs:config/oc-access-points:access-points/oc-access-points:access-point/oc-ap-if:interfaces/oc-ap-if:interface/oc-ap-if:ethernet" {
    description
      "Adds poe configuration and state to access-points model";
    uses oc-poe:ncs_template_poe-ethernet-top;
  }
  augment "/ncs:devices/ncs:device/ncs:live-status/oc-access-points:access-points/oc-access-points:access-point/oc-ap-if:interfaces/oc-ap-if:interface/oc-ap-if:ethernet" {
    description
      "Adds poe configuration and state to access-points model";
    uses oc-poe:live_ncs_poe-ethernet-top {
      refine poe {
        tailf:ncs-device-type "netconf";
        tailf:display-when "not(../../../../../../../ncs:module) or ../../../../../../../ncs:module[ncs:name='openconfig-ap-interfaces'] or (../../../../../../../ncs:live-status-protocol[not(ncs:capability)]) or (../../../../../../../ncs:live-status-protocol/ncs:capability/ncs:module[.='openconfig-ap-interfaces'])";
      }
    }
  }
  augment "/ncs:devices/ncs:device/ncs:config/oc-access-points:access-points/oc-access-points:access-point/oc-ap-if:interfaces/oc-ap-if:interface/oc-ap-if:ethernet" {
    description
      "Adds poe configuration and state to access-points model";
    uses oc-poe:poe-ethernet-top {
      refine poe {
        tailf:ncs-device-type "netconf";
        tailf:display-when "not(../../../../../../../ncs:module) or ../../../../../../../ncs:module[ncs:name='openconfig-ap-interfaces']";
      }
    }
  }
  augment "/ncs:compliance/ncs:template/ncs:ned-id/ncs:config/oc-access-points:access-points/oc-access-points:access-point/oc-ap-if:interfaces/oc-ap-if:interface/oc-ap-if:ethernet" {
    description
      "Adds vlan configuration and state to ethernet interfaces.";
    uses oc-vlan:ncs_compliance_template_vlan-switched-top;
  }
  augment "/ncs:devices/ncs:template/ncs:ned-id/ncs:config/oc-access-points:access-points/oc-access-points:access-point/oc-ap-if:interfaces/oc-ap-if:interface/oc-ap-if:ethernet" {
    description
      "Adds vlan configuration and state to ethernet interfaces.";
    uses oc-vlan:ncs_template_vlan-switched-top;
  }
  augment "/ncs:devices/ncs:device/ncs:live-status/oc-access-points:access-points/oc-access-points:access-point/oc-ap-if:interfaces/oc-ap-if:interface/oc-ap-if:ethernet" {
    description
      "Adds vlan configuration and state to ethernet interfaces.";
    uses oc-vlan:live_ncs_vlan-switched-top {
      refine switched-vlan {
        tailf:ncs-device-type "netconf";
        tailf:display-when "not(../../../../../../../ncs:module) or ../../../../../../../ncs:module[ncs:name='openconfig-ap-interfaces'] or (../../../../../../../ncs:live-status-protocol[not(ncs:capability)]) or (../../../../../../../ncs:live-status-protocol/ncs:capability/ncs:module[.='openconfig-ap-interfaces'])";
      }
    }
  }
  augment "/ncs:devices/ncs:device/ncs:config/oc-access-points:access-points/oc-access-points:access-point/oc-ap-if:interfaces/oc-ap-if:interface/oc-ap-if:ethernet" {
    description
      "Adds vlan configuration and state to ethernet interfaces.";
    uses oc-vlan:vlan-switched-top {
      refine switched-vlan {
        tailf:ncs-device-type "netconf";
        tailf:display-when "not(../../../../../../../ncs:module) or ../../../../../../../ncs:module[ncs:name='openconfig-ap-interfaces']";
      }
    }
  }
  augment "/ncs:compliance/ncs:template/ncs:ned-id/ncs:config/oc-access-points:access-points/oc-access-points:access-point/oc-ap-if:interfaces/oc-ap-if:interface/oc-ap-if:aggregation" {
    description
      "Adds vlan configuration and state to lag interfaces.";
    uses oc-vlan:ncs_compliance_template_vlan-switched-top;
  }
  augment "/ncs:devices/ncs:template/ncs:ned-id/ncs:config/oc-access-points:access-points/oc-access-points:access-point/oc-ap-if:interfaces/oc-ap-if:interface/oc-ap-if:aggregation" {
    description
      "Adds vlan configuration and state to lag interfaces.";
    uses oc-vlan:ncs_template_vlan-switched-top;
  }
  augment "/ncs:devices/ncs:device/ncs:live-status/oc-access-points:access-points/oc-access-points:access-point/oc-ap-if:interfaces/oc-ap-if:interface/oc-ap-if:aggregation" {
    description
      "Adds vlan configuration and state to lag interfaces.";
    uses oc-vlan:live_ncs_vlan-switched-top {
      refine switched-vlan {
        tailf:ncs-device-type "netconf";
        tailf:display-when "not(../../../../../../../ncs:module) or ../../../../../../../ncs:module[ncs:name='openconfig-ap-interfaces'] or (../../../../../../../ncs:live-status-protocol[not(ncs:capability)]) or (../../../../../../../ncs:live-status-protocol/ncs:capability/ncs:module[.='openconfig-ap-interfaces'])";
      }
    }
  }
  augment "/ncs:devices/ncs:device/ncs:config/oc-access-points:access-points/oc-access-points:access-point/oc-ap-if:interfaces/oc-ap-if:interface/oc-ap-if:aggregation" {
    description
      "Adds vlan configuration and state to lag interfaces.";
    uses oc-vlan:vlan-switched-top {
      refine switched-vlan {
        tailf:ncs-device-type "netconf";
        tailf:display-when "not(../../../../../../../ncs:module) or ../../../../../../../ncs:module[ncs:name='openconfig-ap-interfaces']";
      }
    }
  }
  augment "/ncs:compliance/ncs:template/ncs:ned-id/ncs:config/oc-access-points:access-points/oc-access-points:access-point/oc-ap-if:interfaces/oc-ap-if:interface" {
    description
      "Adds tunnel configuration and state to access-points model";
    uses oc-tun:ncs_compliance_template_tunnel-top;
  }
  augment "/ncs:devices/ncs:template/ncs:ned-id/ncs:config/oc-access-points:access-points/oc-access-points:access-point/oc-ap-if:interfaces/oc-ap-if:interface" {
    description
      "Adds tunnel configuration and state to access-points model";
    uses oc-tun:ncs_template_tunnel-top;
  }
  augment "/ncs:devices/ncs:device/ncs:live-status/oc-access-points:access-points/oc-access-points:access-point/oc-ap-if:interfaces/oc-ap-if:interface" {
    description
      "Adds tunnel configuration and state to access-points model";
    uses oc-tun:live_ncs_tunnel-top {
      refine tunnel {
        tailf:ncs-device-type "netconf";
        tailf:display-when "not(../../../../../../ncs:module) or ../../../../../../ncs:module[ncs:name='openconfig-ap-interfaces'] or (../../../../../../ncs:live-status-protocol[not(ncs:capability)]) or (../../../../../../ncs:live-status-protocol/ncs:capability/ncs:module[.='openconfig-ap-interfaces'])";
      }
    }
  }
  augment "/ncs:devices/ncs:device/ncs:config/oc-access-points:access-points/oc-access-points:access-point/oc-ap-if:interfaces/oc-ap-if:interface" {
    description
      "Adds tunnel configuration and state to access-points model";
    uses oc-tun:tunnel-top {
      refine tunnel {
        tailf:ncs-device-type "netconf";
        tailf:display-when "not(../../../../../../ncs:module) or ../../../../../../ncs:module[ncs:name='openconfig-ap-interfaces']";
      }
    }
  }
  deviation "/ncs:compliance/ncs:template/ncs:ned-id/ncs:config/oc-access-points:access-points/oc-access-points:access-point/oc-ap-if:interfaces/oc-ap-if:interface/oc-ap-if:subinterfaces/oc-ap-if:subinterface/oc-ap-if:ipv4/oc-ap-if:unnumbered" {
    deviate not-supported;
  }
  deviation "/ncs:devices/ncs:template/ncs:ned-id/ncs:config/oc-access-points:access-points/oc-access-points:access-point/oc-ap-if:interfaces/oc-ap-if:interface/oc-ap-if:subinterfaces/oc-ap-if:subinterface/oc-ap-if:ipv4/oc-ap-if:unnumbered" {
    deviate not-supported;
  }
  deviation "/ncs:devices/ncs:device/ncs:live-status/oc-access-points:access-points/oc-access-points:access-point/oc-ap-if:interfaces/oc-ap-if:interface/oc-ap-if:subinterfaces/oc-ap-if:subinterface/oc-ap-if:ipv4/oc-ap-if:unnumbered" {
    deviate not-supported;
  }
  deviation "/ncs:devices/ncs:device/ncs:config/oc-access-points:access-points/oc-access-points:access-point/oc-ap-if:interfaces/oc-ap-if:interface/oc-ap-if:subinterfaces/oc-ap-if:subinterface/oc-ap-if:ipv4/oc-ap-if:unnumbered" {
    deviate not-supported;
  }
  deviation "/ncs:compliance/ncs:template/ncs:ned-id/ncs:config/oc-access-points:access-points/oc-access-points:access-point/oc-ap-if:interfaces/oc-ap-if:interface/oc-ap-if:subinterfaces/oc-ap-if:subinterface/oc-ap-if:ipv6/oc-ap-if:unnumbered" {
    deviate not-supported;
  }
  deviation "/ncs:devices/ncs:template/ncs:ned-id/ncs:config/oc-access-points:access-points/oc-access-points:access-point/oc-ap-if:interfaces/oc-ap-if:interface/oc-ap-if:subinterfaces/oc-ap-if:subinterface/oc-ap-if:ipv6/oc-ap-if:unnumbered" {
    deviate not-supported;
  }
  deviation "/ncs:devices/ncs:device/ncs:live-status/oc-access-points:access-points/oc-access-points:access-point/oc-ap-if:interfaces/oc-ap-if:interface/oc-ap-if:subinterfaces/oc-ap-if:subinterface/oc-ap-if:ipv6/oc-ap-if:unnumbered" {
    deviate not-supported;
  }
  deviation "/ncs:devices/ncs:device/ncs:config/oc-access-points:access-points/oc-access-points:access-point/oc-ap-if:interfaces/oc-ap-if:interface/oc-ap-if:subinterfaces/oc-ap-if:subinterface/oc-ap-if:ipv6/oc-ap-if:unnumbered" {
    deviate not-supported;
  }
  deviation "/ncs:compliance/ncs:template/ncs:ned-id/ncs:config/oc-access-points:access-points/oc-access-points:access-point/oc-ap-if:interfaces/oc-ap-if:interface/oc-ap-if:tunnel/oc-ap-if:ipv4/oc-ap-if:unnumbered" {
    deviate not-supported;
  }
  deviation "/ncs:devices/ncs:template/ncs:ned-id/ncs:config/oc-access-points:access-points/oc-access-points:access-point/oc-ap-if:interfaces/oc-ap-if:interface/oc-ap-if:tunnel/oc-ap-if:ipv4/oc-ap-if:unnumbered" {
    deviate not-supported;
  }
  deviation "/ncs:devices/ncs:device/ncs:live-status/oc-access-points:access-points/oc-access-points:access-point/oc-ap-if:interfaces/oc-ap-if:interface/oc-ap-if:tunnel/oc-ap-if:ipv4/oc-ap-if:unnumbered" {
    deviate not-supported;
  }
  deviation "/ncs:devices/ncs:device/ncs:config/oc-access-points:access-points/oc-access-points:access-point/oc-ap-if:interfaces/oc-ap-if:interface/oc-ap-if:tunnel/oc-ap-if:ipv4/oc-ap-if:unnumbered" {
    deviate not-supported;
  }
  deviation "/ncs:compliance/ncs:template/ncs:ned-id/ncs:config/oc-access-points:access-points/oc-access-points:access-point/oc-ap-if:interfaces/oc-ap-if:interface/oc-ap-if:tunnel/oc-ap-if:ipv6/oc-ap-if:unnumbered" {
    deviate not-supported;
  }
  deviation "/ncs:devices/ncs:template/ncs:ned-id/ncs:config/oc-access-points:access-points/oc-access-points:access-point/oc-ap-if:interfaces/oc-ap-if:interface/oc-ap-if:tunnel/oc-ap-if:ipv6/oc-ap-if:unnumbered" {
    deviate not-supported;
  }
  deviation "/ncs:devices/ncs:device/ncs:live-status/oc-access-points:access-points/oc-access-points:access-point/oc-ap-if:interfaces/oc-ap-if:interface/oc-ap-if:tunnel/oc-ap-if:ipv6/oc-ap-if:unnumbered" {
    deviate not-supported;
  }
  deviation "/ncs:devices/ncs:device/ncs:config/oc-access-points:access-points/oc-access-points:access-point/oc-ap-if:interfaces/oc-ap-if:interface/oc-ap-if:tunnel/oc-ap-if:ipv6/oc-ap-if:unnumbered" {
    deviate not-supported;
  }
}
