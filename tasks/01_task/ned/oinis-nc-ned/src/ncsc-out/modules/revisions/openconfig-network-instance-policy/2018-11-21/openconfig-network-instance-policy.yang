module openconfig-network-instance-policy {
  // Generated by yanger -t ncs
  tailf:mount-id "oinis-nc-ned-nc-1.0:oinis-nc-ned-nc-1.0";
  tailf:ncs-device-type "netconf";

  yang-version 1;
  namespace "http://openconfig.net/yang/network-instance/policy";
  prefix oc-ni-pol;

  import openconfig-extensions {
    prefix oc-ext;
  }
  import openconfig-routing-policy {
    prefix oc-rpol;
  }
  import openconfig-policy-types {
    prefix oc-pol-types;
  }
  import tailf-common {
    prefix tailf;
  }
  import tailf-ncs {
    prefix ncs;
  }

  organization
    "OpenConfig working group";
  contact
    "OpenConfig working group
     www.openconfig.net";
  description
    "This module defines routing policy statements (conditions and
     actions) for the network instance model.  These statements are
     generally added to the routing policy model.";
  oc-ext:openconfig-version "0.1.1";

  revision 2018-11-21 {
    description
      "Add OpenConfig module metadata extensions.";
    reference "0.1.1";
  }
  revision 2017-02-15 {
    description
      "Initial revision";
    reference "0.1.0";
  }
  oc-ext:regexp-posix;
  oc-ext:catalog-organization "openconfig";
  oc-ext:origin "openconfig";

  grouping ncs_compliance_template_protocol-instance-policy-config {
    description
      "Configuration data for policy matching on protocol instance";
    leaf protocol-identifier {
      type string;
      description
        "The identifier (protocol type) of the
         protocol instance to match on in the local network
         instance.";
    }
    leaf protocol-name {
      type string;
      description
        "The name of the protocol instance to match
         on in the local network instance";
    }
  }

  grouping ncs_compliance_template_protocol-instance-policy-state {
    description
      "Operational state data for policy matching on protocol
       instance";
  }

  grouping ncs_compliance_template_protocol-instance-policy-top {
    description
      "Top-level grouping for policy matching on protocol instance";
    container match-protocol-instance {
      description
        "Top-level container for protocol instance match condition
         in policy statements.  The protocol instance is referenced
         by an identifier and name";
      container config {
        description
          "Configuration data for policy matching on protocol
           instance";
        uses ncs_compliance_template_protocol-instance-policy-config;
      }
      // NCS drop config false container state
    }
  }

  grouping ncs_template_protocol-instance-policy-config {
    description
      "Configuration data for policy matching on protocol instance";
    leaf protocol-identifier {
      type string;
      description
        "The identifier (protocol type) of the
         protocol instance to match on in the local network
         instance.";
    }
    leaf protocol-name {
      type string;
      description
        "The name of the protocol instance to match
         on in the local network instance";
    }
  }

  grouping ncs_template_protocol-instance-policy-state {
    description
      "Operational state data for policy matching on protocol
       instance";
  }

  grouping ncs_template_protocol-instance-policy-top {
    description
      "Top-level grouping for policy matching on protocol instance";
    container match-protocol-instance {
      description
        "Top-level container for protocol instance match condition
         in policy statements.  The protocol instance is referenced
         by an identifier and name";
      container config {
        description
          "Configuration data for policy matching on protocol
           instance";
        uses ncs_template_protocol-instance-policy-config;
      }
      // NCS drop config false container state
    }
  }

  grouping ncs_rpc_notif_protocol-instance-policy-config {
    description
      "Configuration data for policy matching on protocol instance";
    leaf protocol-identifier {
      type identityref {
        base oc-pol-types:INSTALL_PROTOCOL_TYPE;
      }
      description
        "The identifier (protocol type) of the
         protocol instance to match on in the local network
         instance.";
    }
    leaf protocol-name {
      type string;
      description
        "The name of the protocol instance to match
         on in the local network instance";
    }
  }

  grouping ncs_rpc_notif_protocol-instance-policy-state {
    description
      "Operational state data for policy matching on protocol
       instance";
  }

  grouping ncs_rpc_notif_protocol-instance-policy-top {
    description
      "Top-level grouping for policy matching on protocol instance";
    container match-protocol-instance {
      description
        "Top-level container for protocol instance match condition
         in policy statements.  The protocol instance is referenced
         by an identifier and name";
      container config {
        description
          "Configuration data for policy matching on protocol
           instance";
        uses ncs_rpc_notif_protocol-instance-policy-config;
      }
      container state {
        config false;
        description
          "Operational state data for policy matching on protocol instance";
        uses ncs_rpc_notif_protocol-instance-policy-config;
        uses ncs_rpc_notif_protocol-instance-policy-state;
      }
    }
  }

  grouping live_ncs_protocol-instance-policy-config {
    description
      "Configuration data for policy matching on protocol instance";
    leaf protocol-identifier {
      type identityref {
        base oc-pol-types:INSTALL_PROTOCOL_TYPE;
      }
      description
        "The identifier (protocol type) of the
         protocol instance to match on in the local network
         instance.";
    }
    leaf protocol-name {
      type string;
      description
        "The name of the protocol instance to match
         on in the local network instance";
    }
  }

  grouping live_ncs_protocol-instance-policy-state {
    description
      "Operational state data for policy matching on protocol
       instance";
  }

  grouping live_ncs_protocol-instance-policy-top {
    description
      "Top-level grouping for policy matching on protocol instance";
    container match-protocol-instance {
      description
        "Top-level container for protocol instance match condition
         in policy statements.  The protocol instance is referenced
         by an identifier and name";
      container config {
        description
          "Configuration data for policy matching on protocol
           instance";
        uses live_ncs_protocol-instance-policy-config;
      }
      container state {
        description
          "Operational state data for policy matching on protocol instance";
        uses live_ncs_protocol-instance-policy-config;
        uses live_ncs_protocol-instance-policy-state;
      }
    }
  }

  grouping protocol-instance-policy-config {
    description
      "Configuration data for policy matching on protocol instance";
    leaf protocol-identifier {
      type identityref {
        base oc-pol-types:INSTALL_PROTOCOL_TYPE;
      }
      description
        "The identifier (protocol type) of the
         protocol instance to match on in the local network
         instance.";
    }
    leaf protocol-name {
      type string;
      description
        "The name of the protocol instance to match
         on in the local network instance";
    }
  }

  grouping protocol-instance-policy-state {
    description
      "Operational state data for policy matching on protocol
       instance";
  }

  grouping protocol-instance-policy-top {
    description
      "Top-level grouping for policy matching on protocol instance";
    container match-protocol-instance {
      description
        "Top-level container for protocol instance match condition
         in policy statements.  The protocol instance is referenced
         by an identifier and name";
      container config {
        description
          "Configuration data for policy matching on protocol
           instance";
        uses protocol-instance-policy-config;
      }
      // NCS drop config false container state
    }
  }

  augment "/ncs:compliance/ncs:template/ncs:ned-id/ncs:config/oc-rpol:routing-policy/oc-rpol:policy-definitions/oc-rpol:policy-definition/oc-rpol:statements/oc-rpol:statement/oc-rpol:conditions" {
    description
      "Add match conditions for protocol instances to the routing
       policy model.";
    uses ncs_compliance_template_protocol-instance-policy-top;
  }
  augment "/ncs:devices/ncs:template/ncs:ned-id/ncs:config/oc-rpol:routing-policy/oc-rpol:policy-definitions/oc-rpol:policy-definition/oc-rpol:statements/oc-rpol:statement/oc-rpol:conditions" {
    description
      "Add match conditions for protocol instances to the routing
       policy model.";
    uses ncs_template_protocol-instance-policy-top;
  }
  augment "/ncs:devices/ncs:device/ncs:live-status/oc-rpol:routing-policy/oc-rpol:policy-definitions/oc-rpol:policy-definition/oc-rpol:statements/oc-rpol:statement/oc-rpol:conditions" {
    description
      "Add match conditions for protocol instances to the routing
       policy model.";
    uses live_ncs_protocol-instance-policy-top {
      refine match-protocol-instance {
        tailf:ncs-device-type "netconf";
        tailf:display-when "not(../../../../../../../../ncs:module) or ../../../../../../../../ncs:module[ncs:name='openconfig-network-instance-policy'] or (../../../../../../../../ncs:live-status-protocol[not(ncs:capability)]) or (../../../../../../../../ncs:live-status-protocol/ncs:capability/ncs:module[.='openconfig-network-instance-policy'])";
      }
    }
  }
  augment "/ncs:devices/ncs:device/ncs:config/oc-rpol:routing-policy/oc-rpol:policy-definitions/oc-rpol:policy-definition/oc-rpol:statements/oc-rpol:statement/oc-rpol:conditions" {
    description
      "Add match conditions for protocol instances to the routing
       policy model.";
    uses protocol-instance-policy-top {
      refine match-protocol-instance {
        tailf:ncs-device-type "netconf";
        tailf:display-when "not(../../../../../../../../ncs:module) or ../../../../../../../../ncs:module[ncs:name='openconfig-network-instance-policy']";
      }
    }
  }
}
