module openconfig-mpls-types {
  // Generated by yanger -t ncs
  tailf:mount-id "oinis-nc-ned-nc-1.0:oinis-nc-ned-nc-1.0";
  tailf:ncs-device-type "netconf";

  yang-version 1;
  namespace "http://openconfig.net/yang/mpls-types";
  prefix oc-mplst;

  import openconfig-extensions {
    prefix oc-ext;
  }
  import tailf-common {
    prefix tailf;
  }
  import tailf-ncs {
    prefix ncs;
  }

  organization
    "OpenConfig working group";
  contact
    "OpenConfig working group
     netopenconfig@googlegroups.com";
  description
    "General types for MPLS / TE data model";
  oc-ext:openconfig-version "3.4.0";

  revision 2021-12-01 {
    description
      "Add new identity for RSVP authentication types";
    reference "3.4.0";
  }
  revision 2021-06-16 {
    description
      "Remove trailing whitespace";
    reference "3.3.1";
  }
  revision 2021-03-23 {
    description
      "Add new identity for path metric types.";
    reference "3.3.0";
  }
  revision 2020-02-04 {
    description
      "Consistent prefix for openconfig-mpls-types.";
    reference "3.2.0";
  }
  revision 2019-03-26 {
    description
      "Add Pseudowire encapsulation.";
    reference "3.1.0";
  }
  revision 2018-11-21 {
    description
      "Add OpenConfig module metadata extensions.";
    reference "3.0.1";
  }
  revision 2018-07-02 {
    description
      "Add new RSVP-TE statistics, remove associated-rsvp-session
       leaf. Remove use of date-and-time.";
    reference "3.0.0";
  }
  revision 2018-06-16 {
    description
      "Included attributes for base LDP configuration.";
    reference "2.6.0";
  }
  revision 2018-06-13 {
    description
      "Add ttl-propagation to global MPLS config";
    reference "2.5.0";
  }
  revision 2018-06-05 {
    description
      "Fixed bugs in when statements on RSVP-TE attributes";
    reference "2.4.2";
  }
  revision 2017-08-24 {
    description
      "Minor formatting fixes.";
    reference "2.4.1";
  }
  revision 2017-06-21 {
    description
      "Add TC bits typedef.";
    reference "2.4.0";
  }
  revision 2017-03-22 {
    description
      "Add RSVP calculated-absolute-subscription-bw";
    reference "2.3.0";
  }
  revision 2017-01-26 {
    description
      "Add RSVP Tspec, clarify units for RSVP, remove unused LDP";
    reference "2.2.0";
  }
  revision 2016-12-15 {
    description
      "Add additional MPLS parameters";
    reference "2.1.0";
  }
  revision 2016-09-01 {
    description
      "Revisions based on implementation feedback";
    reference "2.0.0";
  }
  revision 2016-08-08 {
    description
      "Public release of MPLS models";
    reference "1.0.1";
  }

  typedef ncs_compliance_template_mpls-label {
    type string;
    description
      "type for MPLS label value encoding";
    reference "RFC 3032 - MPLS Label Stack Encoding";
  }

  typedef ncs_compliance_template_tunnel-type {
    type string;
    description
      "defines the tunnel type for the LSP";
    reference
      "RFC 6388 - Label Distribution Protocol Extensions for
       Point-to-Multipoint and Multipoint-to-Multipoint Label Switched
       Paths
       RFC 4875 - Extensions to  Resource Reservation Protocol
       - Traffic Engineering (RSVP-TE) for Point-to-Multipoint TE
       Label Switched Paths (LSPs)";
  }

  typedef ncs_compliance_template_bandwidth-kbps {
    type string;
    units "Kbps";
    description
      "Bandwidth values expressed in kilobits per second";
  }

  typedef ncs_compliance_template_bandwidth-mbps {
    type string;
    units "Mbps";
    description
      "Bandwidth values expressed in megabits per second";
  }

  typedef ncs_compliance_template_bandwidth-gbps {
    type string;
    units "Gbps";
    description
      "Bandwidth values expressed in gigabits per second";
  }

  typedef ncs_compliance_template_mpls-tc {
    type string;
    description
      "Values of the MPLS Traffic Class (formerly known as
       Experimental, EXP) bits";
  }

  typedef ncs_template_mpls-label {
    type string;
    description
      "type for MPLS label value encoding";
    reference "RFC 3032 - MPLS Label Stack Encoding";
  }

  typedef ncs_template_tunnel-type {
    type string;
    description
      "defines the tunnel type for the LSP";
    reference
      "RFC 6388 - Label Distribution Protocol Extensions for
       Point-to-Multipoint and Multipoint-to-Multipoint Label Switched
       Paths
       RFC 4875 - Extensions to  Resource Reservation Protocol
       - Traffic Engineering (RSVP-TE) for Point-to-Multipoint TE
       Label Switched Paths (LSPs)";
  }

  typedef ncs_template_bandwidth-kbps {
    type string;
    units "Kbps";
    description
      "Bandwidth values expressed in kilobits per second";
  }

  typedef ncs_template_bandwidth-mbps {
    type string;
    units "Mbps";
    description
      "Bandwidth values expressed in megabits per second";
  }

  typedef ncs_template_bandwidth-gbps {
    type string;
    units "Gbps";
    description
      "Bandwidth values expressed in gigabits per second";
  }

  typedef ncs_template_mpls-tc {
    type string;
    description
      "Values of the MPLS Traffic Class (formerly known as
       Experimental, EXP) bits";
  }

  typedef ncs_rpc_notif_mpls-label {
    type union {
      type uint32 {
        range "16..1048575";
      }
      type enumeration {
        enum "IPV4_EXPLICIT_NULL" {
          value 0;
          description
            "valid at the bottom of the label stack,
             indicates that stack must be popped and packet forwarded
             based on IPv4 header";
        }
        enum "ROUTER_ALERT" {
          value 1;
          description
            "allowed anywhere in the label stack except
             the bottom, local router delivers packet to the local CPU
             when this label is at the top of the stack";
        }
        enum "IPV6_EXPLICIT_NULL" {
          value 2;
          description
            "valid at the bottom of the label stack,
             indicates that stack must be popped and packet forwarded
             based on IPv6 header";
        }
        enum "IMPLICIT_NULL" {
          value 3;
          description
            "assigned by local LSR but not carried in
             packets";
        }
        enum "ENTROPY_LABEL_INDICATOR" {
          value 7;
          description
            "Entropy label indicator, to allow an LSR
             to distinguish between entropy label and applicaiton
             labels RFC 6790";
        }
        enum "NO_LABEL" {
          description
            "This value is utilised to indicate that the packet that
             is forwarded by the local system does not have an MPLS
             header applied to it. Typically, this is used at the
             egress of an LSP";
        }
      }
    }
    description
      "type for MPLS label value encoding";
    reference "RFC 3032 - MPLS Label Stack Encoding";
  }

  typedef ncs_rpc_notif_tunnel-type {
    type enumeration {
      enum "P2P" {
        description
          "point-to-point label-switched-path";
      }
      enum "P2MP" {
        description
          "point-to-multipoint label-switched-path";
      }
      enum "MP2MP" {
        description
          "multipoint-to-multipoint label-switched-path";
      }
    }
    description
      "defines the tunnel type for the LSP";
    reference
      "RFC 6388 - Label Distribution Protocol Extensions for
       Point-to-Multipoint and Multipoint-to-Multipoint Label Switched
       Paths
       RFC 4875 - Extensions to  Resource Reservation Protocol
       - Traffic Engineering (RSVP-TE) for Point-to-Multipoint TE
       Label Switched Paths (LSPs)";
  }

  typedef ncs_rpc_notif_bandwidth-kbps {
    type uint64;
    units "Kbps";
    description
      "Bandwidth values expressed in kilobits per second";
  }

  typedef ncs_rpc_notif_bandwidth-mbps {
    type uint64;
    units "Mbps";
    description
      "Bandwidth values expressed in megabits per second";
  }

  typedef ncs_rpc_notif_bandwidth-gbps {
    type uint64;
    units "Gbps";
    description
      "Bandwidth values expressed in gigabits per second";
  }

  typedef ncs_rpc_notif_mpls-tc {
    type uint8 {
      range "0..7";
    }
    description
      "Values of the MPLS Traffic Class (formerly known as
       Experimental, EXP) bits";
  }

  typedef live_ncs_mpls-label {
    type union {
      type uint32 {
        range "16..1048575";
      }
      type enumeration {
        enum "IPV4_EXPLICIT_NULL" {
          value 0;
          description
            "valid at the bottom of the label stack,
             indicates that stack must be popped and packet forwarded
             based on IPv4 header";
        }
        enum "ROUTER_ALERT" {
          value 1;
          description
            "allowed anywhere in the label stack except
             the bottom, local router delivers packet to the local CPU
             when this label is at the top of the stack";
        }
        enum "IPV6_EXPLICIT_NULL" {
          value 2;
          description
            "valid at the bottom of the label stack,
             indicates that stack must be popped and packet forwarded
             based on IPv6 header";
        }
        enum "IMPLICIT_NULL" {
          value 3;
          description
            "assigned by local LSR but not carried in
             packets";
        }
        enum "ENTROPY_LABEL_INDICATOR" {
          value 7;
          description
            "Entropy label indicator, to allow an LSR
             to distinguish between entropy label and applicaiton
             labels RFC 6790";
        }
        enum "NO_LABEL" {
          description
            "This value is utilised to indicate that the packet that
             is forwarded by the local system does not have an MPLS
             header applied to it. Typically, this is used at the
             egress of an LSP";
        }
      }
    }
    description
      "type for MPLS label value encoding";
    reference "RFC 3032 - MPLS Label Stack Encoding";
  }

  typedef live_ncs_tunnel-type {
    type enumeration {
      enum "P2P" {
        description
          "point-to-point label-switched-path";
      }
      enum "P2MP" {
        description
          "point-to-multipoint label-switched-path";
      }
      enum "MP2MP" {
        description
          "multipoint-to-multipoint label-switched-path";
      }
    }
    description
      "defines the tunnel type for the LSP";
    reference
      "RFC 6388 - Label Distribution Protocol Extensions for
       Point-to-Multipoint and Multipoint-to-Multipoint Label Switched
       Paths
       RFC 4875 - Extensions to  Resource Reservation Protocol
       - Traffic Engineering (RSVP-TE) for Point-to-Multipoint TE
       Label Switched Paths (LSPs)";
  }

  typedef live_ncs_bandwidth-kbps {
    type uint64;
    units "Kbps";
    description
      "Bandwidth values expressed in kilobits per second";
  }

  typedef live_ncs_bandwidth-mbps {
    type uint64;
    units "Mbps";
    description
      "Bandwidth values expressed in megabits per second";
  }

  typedef live_ncs_bandwidth-gbps {
    type uint64;
    units "Gbps";
    description
      "Bandwidth values expressed in gigabits per second";
  }

  typedef live_ncs_mpls-tc {
    type uint8 {
      range "0..7";
    }
    description
      "Values of the MPLS Traffic Class (formerly known as
       Experimental, EXP) bits";
  }

  typedef mpls-label {
    type union {
      type uint32 {
        range "16..1048575";
      }
      type enumeration {
        enum "IPV4_EXPLICIT_NULL" {
          value 0;
          description
            "valid at the bottom of the label stack,
             indicates that stack must be popped and packet forwarded
             based on IPv4 header";
        }
        enum "ROUTER_ALERT" {
          value 1;
          description
            "allowed anywhere in the label stack except
             the bottom, local router delivers packet to the local CPU
             when this label is at the top of the stack";
        }
        enum "IPV6_EXPLICIT_NULL" {
          value 2;
          description
            "valid at the bottom of the label stack,
             indicates that stack must be popped and packet forwarded
             based on IPv6 header";
        }
        enum "IMPLICIT_NULL" {
          value 3;
          description
            "assigned by local LSR but not carried in
             packets";
        }
        enum "ENTROPY_LABEL_INDICATOR" {
          value 7;
          description
            "Entropy label indicator, to allow an LSR
             to distinguish between entropy label and applicaiton
             labels RFC 6790";
        }
        enum "NO_LABEL" {
          description
            "This value is utilised to indicate that the packet that
             is forwarded by the local system does not have an MPLS
             header applied to it. Typically, this is used at the
             egress of an LSP";
        }
      }
    }
    description
      "type for MPLS label value encoding";
    reference "RFC 3032 - MPLS Label Stack Encoding";
  }

  typedef tunnel-type {
    type enumeration {
      enum "P2P" {
        description
          "point-to-point label-switched-path";
      }
      enum "P2MP" {
        description
          "point-to-multipoint label-switched-path";
      }
      enum "MP2MP" {
        description
          "multipoint-to-multipoint label-switched-path";
      }
    }
    description
      "defines the tunnel type for the LSP";
    reference
      "RFC 6388 - Label Distribution Protocol Extensions for
       Point-to-Multipoint and Multipoint-to-Multipoint Label Switched
       Paths
       RFC 4875 - Extensions to  Resource Reservation Protocol
       - Traffic Engineering (RSVP-TE) for Point-to-Multipoint TE
       Label Switched Paths (LSPs)";
  }

  typedef bandwidth-kbps {
    type uint64;
    units "Kbps";
    description
      "Bandwidth values expressed in kilobits per second";
  }

  typedef bandwidth-mbps {
    type uint64;
    units "Mbps";
    description
      "Bandwidth values expressed in megabits per second";
  }

  typedef bandwidth-gbps {
    type uint64;
    units "Gbps";
    description
      "Bandwidth values expressed in gigabits per second";
  }

  typedef mpls-tc {
    type uint8 {
      range "0..7";
    }
    description
      "Values of the MPLS Traffic Class (formerly known as
       Experimental, EXP) bits";
  }

  identity RSVP_AUTH_MD5 {
    base RSVP_AUTH_TYPE;
    description
      "HMAC-MD5 message authentication";
  }

  identity RSVP_AUTH_TYPE {
    description
      "Base identity for RSVP message authentication types";
    reference "RFC2747: RSVP Cryptographic Authentication";
  }

  identity PATH_DELAY {
    base PATH_METRIC_TYPE;
    description
      "Unidirectional average link delay.
       It represents the sum of the Link Delay metric
       of all links along a P2P path.";
    reference
      "RFC8570 IS-IS Traffic Engineering (TE) Metric Extensions.
       RFC7471 OSPF Traffic Engineering (TE) Metric Extensions.
       RFC 8233: Extensions to the Path Computation Element Communication Protocol (PCEP)
       to Compute Service-Aware Label Switched Paths (LSPs) Path Computation Element (PCE)
       Communication Protocol (PCEP).";
  }

  identity HOP_COUNT {
    base PATH_METRIC_TYPE;
    description
      "Hop count path metric.";
    reference "RFC5440: Path Computation Element (PCE) Communication Protocol (PCEP).";
  }

  identity IGP_METRIC {
    base PATH_METRIC_TYPE;
    description
      "IGP path metric.";
    reference "RFC5440: Path Computation Element (PCE) Communication Protocol (PCEP).";
  }

  identity TE_METRIC {
    base PATH_METRIC_TYPE;
    description
      "TE path metric.";
    reference
      "RFC3785: Use of Interior Gateway Protocol (IGP) Metric as a
       second MPLS Traffic Engineering (TE) Metric.
       RFC5440: Path Computation Element (PCE) Communication Protocol (PCEP).";
  }

  identity PATH_METRIC_TYPE {
    description
      "Base identity for path metric type.";
  }

  identity PWE_ETHERNET_RAW_MODE {
    base PSEUDOWIRE_ENCAPSULATION;
    description
      "Ethernet Raw Mode RFC4448";
    reference "IANA PWE3 0x0005";
  }

  identity PWE_ETHERNET_TAGGED_MODE {
    base PSEUDOWIRE_ENCAPSULATION;
    description
      "Ethernet Tagged Mode RFC4448";
    reference "IANA PWE3 0x0004";
  }

  identity PSEUDOWIRE_ENCAPSULATION {
    description
      "Sets the PDU type of the PSEUDOWIRE Example in RFC4448. This value
       should be enumerated from the IANA Pseudowire types registry";
  }

  identity LSP_METRIC_INHERITED {
    base LSP_METRIC_TYPE;
    description
      "The metric for for the LSPs to which this identity refers is
       not specified explicitly - but rather inherited from the IGP
       cost directly";
  }

  identity LSP_METRIC_ABSOLUTE {
    base LSP_METRIC_TYPE;
    description
      "The metric specified for the LSPs to which this identity refers
       is specified as an absolute value";
  }

  identity LSP_METRIC_RELATIVE {
    base LSP_METRIC_TYPE;
    description
      "The metric specified for the LSPs to which this identity refers
       is specified as a relative value to the IGP metric cost to the
       LSP's tail-end.";
  }

  identity LSP_METRIC_TYPE {
    description
      "Base identity for types of LSP metric specification";
  }

  identity IMPLICIT {
    base NULL_LABEL_TYPE;
    description
      "Implicit null label is used.";
  }

  identity EXPLICIT {
    base NULL_LABEL_TYPE;
    description
      "Explicit null label is used.";
  }

  identity NULL_LABEL_TYPE {
    description
      "Base identity from which specific null-label types are
       derived.";
  }

  identity ADMIN_UP {
    base TUNNEL_ADMIN_STATUS;
    description
      "LSP is administratively up";
  }

  identity ADMIN_DOWN {
    base TUNNEL_ADMIN_STATUS;
    description
      "LSP is administratively down";
  }

  identity TUNNEL_ADMIN_STATUS {
    description
      "Base identity for tunnel administrative status";
  }

  identity UP {
    base LSP_OPER_STATUS;
    description
      "LSP is operationally active and available
       for traffic.";
  }

  identity DOWN {
    base LSP_OPER_STATUS;
    description
      "LSP is operationally down or out of service";
  }

  identity LSP_OPER_STATUS {
    description
      "Base identity for LSP operational status";
  }

  identity P2MP {
    base TUNNEL_TYPE;
    description
      "TE point-to-multipoint tunnel type.";
  }

  identity P2P {
    base TUNNEL_TYPE;
    description
      "TE point-to-point tunnel type.";
  }

  identity TUNNEL_TYPE {
    description
      "Base identity from which specific tunnel types are
       derived.";
  }

  identity TRANSIT {
    base LSP_ROLE;
    description
      "Label switched path is a transit LSP";
  }

  identity EGRESS {
    base LSP_ROLE;
    description
      "Label switched path is an egress (tailend)
       LSP";
  }

  identity INGRESS {
    base LSP_ROLE;
    description
      "Label switched path is an ingress (headend)
       LSP";
  }

  identity LSP_ROLE {
    description
      "Base identity for describing the role of
       label switched path at the current node";
  }

  identity LINK_NODE_PROTECTION_REQUESTED {
    base PROTECTION_TYPE;
    description
      "node and link protection are both desired";
  }

  identity LINK_PROTECTION_REQUIRED {
    base PROTECTION_TYPE;
    description
      "link protection is desired";
  }

  identity UNPROTECTED {
    base PROTECTION_TYPE;
    description
      "no protection is desired";
  }

  identity PROTECTION_TYPE {
    description
      "base identity for protection type";
  }

  identity PATH_SETUP_LDP {
    base PATH_SETUP_PROTOCOL;
    description
      "LDP - RFC 5036";
  }

  identity PATH_SETUP_SR {
    base PATH_SETUP_PROTOCOL;
    description
      "Segment routing";
  }

  identity PATH_SETUP_RSVP {
    base PATH_SETUP_PROTOCOL;
    description
      "RSVP-TE signaling protocol";
  }

  identity PATH_SETUP_PROTOCOL {
    description
      "base identity for supported MPLS signaling
       protocols";
  }

  identity EXPLICITLY_DEFINED {
    base PATH_COMPUTATION_METHOD;
    description
      "constrained-path LSP in which the path is
       explicitly specified as a collection of strict or/and loose
       hops";
  }

  identity EXTERNALLY_QUERIED {
    base PATH_COMPUTATION_METHOD;
    description
      "Constrained-path LSP in which the path is
       obtained by querying an external source, such as a PCE server.
       In the case that an LSP is defined to be externally queried, it may
       also have associated explicit definitions (which are provided to the
       external source to aid computation); and the path that is returned by
       the external source is not required to provide a wholly resolved
       path back to the originating system - that is to say, some local
       computation may also be required";
  }

  identity LOCALLY_COMPUTED {
    base PATH_COMPUTATION_METHOD;
    description
      "indicates a constrained-path LSP in which the
       path is computed by the local LER";
  }

  identity PATH_COMPUTATION_METHOD {
    description
      "base identity for supported path computation
       mechanisms";
  }
}
