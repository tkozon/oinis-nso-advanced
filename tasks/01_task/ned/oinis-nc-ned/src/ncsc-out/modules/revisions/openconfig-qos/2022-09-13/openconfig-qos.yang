module openconfig-qos {
  // Generated by yanger -t ncs
  tailf:mount-id "oinis-nc-ned-nc-1.0:oinis-nc-ned-nc-1.0";
  tailf:ncs-device-type "netconf";

  yang-version 1;
  namespace "http://openconfig.net/yang/qos";
  prefix oc-qos;

  import openconfig-extensions {
    prefix oc-ext;
  }
  include openconfig-qos-interfaces;
  include openconfig-qos-elements;
  include openconfig-qos-mem-mgmt;
  import tailf-common {
    prefix tailf;
  }
  import tailf-ncs {
    prefix ncs;
  }

  organization
    "OpenConfig working group";
  contact
    "OpenConfig working group
     www.openconfig.net";
  description
    "This module defines configuration and operational state data
     related to network quality-of-service.";
  oc-ext:openconfig-version "0.6.0";

  revision 2022-09-13 {
    description
      "Add queue octet drop counter.";
    reference "0.6.0";
  }
  revision 2021-08-28 {
    description
      "Revision using latest revision of openconfig-qos-mem-mgmt submodule.";
    reference "0.5.0";
  }
  revision 2021-06-28 {
    description
      "Revision to include buffer-allocation-profile-q-config
       parameters in openconfig-qos-mem-mgmt submodule.";
    reference "0.4.0";
  }
  revision 2021-04-28 {
    description
      "Revision updating buffer management and queue management
       configuration.";
    reference "0.3.0";
  }
  revision 2019-11-28 {
    description
      "Fix xpaths in when statements";
    reference "0.2.3";
  }
  revision 2019-08-20 {
    description
      "Fix typo in classifiers container name";
    reference "0.2.2";
  }
  revision 2018-11-21 {
    description
      "Add OpenConfig module metadata extensions.";
    reference "0.2.1";
  }
  revision 2016-12-16 {
    description
      "Fix incorrect interface-ref placement";
    reference "0.2.0";
  }
  oc-ext:regexp-posix;
  oc-ext:catalog-organization "openconfig";
  oc-ext:origin "openconfig";

  grouping ncs_compliance_template_qos-config {
    description
      "Configuration data for global QoS";
  }

  grouping ncs_compliance_template_qos-state {
    description
      "Operational state data for global QoS";
  }

  grouping ncs_compliance_template_qos-top {
    description
      "Top-level grouping for QoS model";
    container qos {
      description
        "Top-level container for QoS data";
      container config {
        description
          "Configuration data for global QoS";
        uses ncs_compliance_template_qos-config;
      }
      // NCS drop config false container state
      uses ncs_compliance_template_qos-interfaces-top;
      uses ncs_compliance_template_qos-classifier-top;
      uses ncs_compliance_template_qos-forwarding-group-top;
      uses ncs_compliance_template_qos-queue-top;
      uses ncs_compliance_template_qos-scheduler-top;
      uses ncs_compliance_template_qos-buffer-profile-top;
      uses ncs_compliance_template_qos-queue-mgmt-profile-top;
    }
  }

  grouping ncs_template_qos-config {
    description
      "Configuration data for global QoS";
  }

  grouping ncs_template_qos-state {
    description
      "Operational state data for global QoS";
  }

  grouping ncs_template_qos-top {
    description
      "Top-level grouping for QoS model";
    container qos {
      description
        "Top-level container for QoS data";
      container config {
        description
          "Configuration data for global QoS";
        uses ncs_template_qos-config;
      }
      // NCS drop config false container state
      uses ncs_template_qos-interfaces-top;
      uses ncs_template_qos-classifier-top;
      uses ncs_template_qos-forwarding-group-top;
      uses ncs_template_qos-queue-top;
      uses ncs_template_qos-scheduler-top;
      uses ncs_template_qos-buffer-profile-top;
      uses ncs_template_qos-queue-mgmt-profile-top;
    }
  }

  grouping ncs_rpc_notif_qos-config {
    description
      "Configuration data for global QoS";
  }

  grouping ncs_rpc_notif_qos-state {
    description
      "Operational state data for global QoS";
  }

  grouping ncs_rpc_notif_qos-top {
    description
      "Top-level grouping for QoS model";
    container qos {
      description
        "Top-level container for QoS data";
      container config {
        description
          "Configuration data for global QoS";
        uses ncs_rpc_notif_qos-config;
      }
      container state {
        config false;
        description
          "Operational state data for global QoS";
        uses ncs_rpc_notif_qos-config;
        uses ncs_rpc_notif_qos-state;
      }
      uses ncs_rpc_notif_qos-interfaces-top;
      uses ncs_rpc_notif_qos-classifier-top;
      uses ncs_rpc_notif_qos-forwarding-group-top;
      uses ncs_rpc_notif_qos-queue-top;
      uses ncs_rpc_notif_qos-scheduler-top;
      uses ncs_rpc_notif_qos-buffer-profile-top;
      uses ncs_rpc_notif_qos-queue-mgmt-profile-top;
    }
  }

  grouping live_ncs_qos-config {
    description
      "Configuration data for global QoS";
  }

  grouping live_ncs_qos-state {
    description
      "Operational state data for global QoS";
  }

  grouping live_ncs_qos-top {
    description
      "Top-level grouping for QoS model";
    container qos {
      description
        "Top-level container for QoS data";
      container config {
        description
          "Configuration data for global QoS";
        uses live_ncs_qos-config;
      }
      container state {
        description
          "Operational state data for global QoS";
        uses live_ncs_qos-config;
        uses live_ncs_qos-state;
      }
      uses live_ncs_qos-interfaces-top;
      uses live_ncs_qos-classifier-top;
      uses live_ncs_qos-forwarding-group-top;
      uses live_ncs_qos-queue-top;
      uses live_ncs_qos-scheduler-top;
      uses live_ncs_qos-buffer-profile-top;
      uses live_ncs_qos-queue-mgmt-profile-top;
    }
  }

  grouping qos-config {
    description
      "Configuration data for global QoS";
  }

  grouping qos-state {
    description
      "Operational state data for global QoS";
  }

  grouping qos-top {
    description
      "Top-level grouping for QoS model";
    container qos {
      description
        "Top-level container for QoS data";
      container config {
        description
          "Configuration data for global QoS";
        uses qos-config;
      }
      // NCS drop config false container state
      uses qos-interfaces-top;
      uses qos-classifier-top;
      uses qos-forwarding-group-top;
      uses qos-queue-top;
      uses qos-scheduler-top;
      uses qos-buffer-profile-top;
      uses qos-queue-mgmt-profile-top;
    }
  }

  augment "/ncs:devices/ncs:device/ncs:config" {
    uses qos-top {
      refine qos {
        tailf:ncs-device-type "netconf";
        tailf:display-when "not(../../ncs:module) or ../../ncs:module[ncs:name='openconfig-qos']";
      }
    }
  }
  augment "/ncs:devices/ncs:device/ncs:live-status" {
    uses live_ncs_qos-top {
      refine qos {
        tailf:ncs-device-type "netconf";
        tailf:display-when "not(../../ncs:module) or ../../ncs:module[ncs:name='openconfig-qos'] or (../../ncs:live-status-protocol[not(ncs:capability)]) or (../../ncs:live-status-protocol/ncs:capability/ncs:module[.='openconfig-qos'])";
      }
    }
  }
  augment "/ncs:devices/ncs:template/ncs:ned-id/ncs:config" {
    uses ncs_template_qos-top;
  }
  augment "/ncs:compliance/ncs:template/ncs:ned-id/ncs:config" {
    uses ncs_compliance_template_qos-top;
  }
}
