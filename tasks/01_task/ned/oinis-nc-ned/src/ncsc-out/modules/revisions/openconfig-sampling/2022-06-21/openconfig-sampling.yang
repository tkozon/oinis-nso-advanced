module openconfig-sampling {
  // Generated by yanger -t ncs
  tailf:mount-id "oinis-nc-ned-nc-1.0:oinis-nc-ned-nc-1.0";
  tailf:ncs-device-type "netconf";

  yang-version 1;
  namespace "http://openconfig.net/yang/sampling";
  prefix oc-sampling;

  import openconfig-extensions {
    prefix oc-ext;
  }
  import tailf-common {
    prefix tailf;
  }
  import tailf-ncs {
    prefix ncs;
  }

  organization
    "OpenConfig working group";
  contact
    "OpenConfig working group
     www.openconfig.net";
  description
    "This module defines top-level configuration and operational
     state data related to traffic sampling.

     For modularity purposes, the top-level sampling container provides
     a natural attachment point for implementations such as sFlow, IPFix,
     NETFLOW";

  revision 2022-06-21 {
    description
      "Initial revision";
    reference "0.1.0";
  }
  oc-ext:openconfig-version "0.1.0";

  grouping ncs_compliance_template_sampling-top {
    description
      "Top level sampling containers";
    container sampling {
      description
        "Top-level container for sampling-related configuration and
         operational state data";
    }
  }

  grouping ncs_template_sampling-top {
    description
      "Top level sampling containers";
    container sampling {
      description
        "Top-level container for sampling-related configuration and
         operational state data";
    }
  }

  grouping ncs_rpc_notif_sampling-top {
    description
      "Top level sampling containers";
    container sampling {
      description
        "Top-level container for sampling-related configuration and
         operational state data";
    }
  }

  grouping live_ncs_sampling-top {
    description
      "Top level sampling containers";
    container sampling {
      description
        "Top-level container for sampling-related configuration and
         operational state data";
    }
  }

  grouping sampling-top {
    description
      "Top level sampling containers";
    container sampling {
      description
        "Top-level container for sampling-related configuration and
         operational state data";
    }
  }

  augment "/ncs:devices/ncs:device/ncs:config" {
    uses sampling-top {
      refine sampling {
        tailf:ncs-device-type "netconf";
        tailf:display-when "not(../../ncs:module) or ../../ncs:module[ncs:name='openconfig-sampling']";
      }
    }
  }
  augment "/ncs:devices/ncs:device/ncs:live-status" {
    uses live_ncs_sampling-top {
      refine sampling {
        tailf:ncs-device-type "netconf";
        tailf:display-when "not(../../ncs:module) or ../../ncs:module[ncs:name='openconfig-sampling'] or (../../ncs:live-status-protocol[not(ncs:capability)]) or (../../ncs:live-status-protocol/ncs:capability/ncs:module[.='openconfig-sampling'])";
      }
    }
  }
  augment "/ncs:devices/ncs:template/ncs:ned-id/ncs:config" {
    uses ncs_template_sampling-top;
  }
  augment "/ncs:compliance/ncs:template/ncs:ned-id/ncs:config" {
    uses ncs_compliance_template_sampling-top;
  }
}
