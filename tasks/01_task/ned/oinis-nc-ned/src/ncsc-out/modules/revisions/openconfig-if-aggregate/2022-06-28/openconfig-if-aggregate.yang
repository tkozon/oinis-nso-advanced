module openconfig-if-aggregate {
  // Generated by yanger -t ncs
  tailf:mount-id "oinis-nc-ned-nc-1.0:oinis-nc-ned-nc-1.0";
  tailf:ncs-device-type "netconf";

  yang-version 1;
  namespace "http://openconfig.net/yang/interfaces/aggregate";
  prefix oc-lag;

  import openconfig-interfaces {
    prefix oc-if;
  }
  import openconfig-if-ethernet {
    prefix oc-eth;
  }
  import iana-if-type {
    prefix ianaift;
  }
  import openconfig-extensions {
    prefix oc-ext;
  }
  import tailf-common {
    prefix tailf;
  }
  import tailf-ncs {
    prefix ncs;
  }

  organization
    "OpenConfig working group";
  contact
    "OpenConfig working group
     netopenconfig@googlegroups.com";
  description
    "Model for managing aggregated (aka bundle, LAG) interfaces.";
  oc-ext:openconfig-version "2.4.4";

  revision 2022-06-28 {
    description
      "Remove reference to invalid oc-ift type check";
    reference "2.4.4";
  }
  revision 2020-05-01 {
    description
      "Update when statements to reference config nodes
       from config true elements.";
    reference "2.4.3";
  }
  revision 2019-04-16 {
    description
      "Update import prefix for iana-if-type module";
    reference "2.4.2";
  }
  revision 2018-11-21 {
    description
      "Add OpenConfig module metadata extensions.";
    reference "2.3.2";
  }
  revision 2018-03-23 {
    description
      "Fix/cleanup when statements in aggregates model.";
    reference "2.3.1";
  }
  revision 2018-01-05 {
    description
      "Add logical loopback to interface.";
    reference "2.3.0";
  }
  revision 2017-12-22 {
    description
      "Add IPv4 proxy ARP configuration.";
    reference "2.2.0";
  }
  revision 2017-12-21 {
    description
      "Added IPv6 router advertisement configuration.";
    reference "2.1.0";
  }
  revision 2017-07-14 {
    description
      "Added Ethernet/IP state data; Add dhcp-client;
       migrate to OpenConfig types modules; Removed or
       renamed opstate values";
    reference "2.0.0";
  }
  revision 2016-12-22 {
    description
      "Fixes to Ethernet interfaces model";
    reference "1.1.0";
  }
  oc-ext:regexp-posix;
  oc-ext:catalog-organization "openconfig";
  oc-ext:origin "openconfig";

  typedef ncs_compliance_template_aggregation-type {
    type string;
    description
      "Type to define the lag-type, i.e., how the LAG is
       defined and managed";
  }

  typedef ncs_template_aggregation-type {
    type string;
    description
      "Type to define the lag-type, i.e., how the LAG is
       defined and managed";
  }

  typedef ncs_rpc_notif_aggregation-type {
    type enumeration {
      enum "LACP" {
        description
          "LAG managed by LACP";
      }
      enum "STATIC" {
        description
          "Statically configured bundle / LAG";
      }
    }
    description
      "Type to define the lag-type, i.e., how the LAG is
       defined and managed";
  }

  typedef live_ncs_aggregation-type {
    type enumeration {
      enum "LACP" {
        description
          "LAG managed by LACP";
      }
      enum "STATIC" {
        description
          "Statically configured bundle / LAG";
      }
    }
    description
      "Type to define the lag-type, i.e., how the LAG is
       defined and managed";
  }

  typedef aggregation-type {
    type enumeration {
      enum "LACP" {
        description
          "LAG managed by LACP";
      }
      enum "STATIC" {
        description
          "Statically configured bundle / LAG";
      }
    }
    description
      "Type to define the lag-type, i.e., how the LAG is
       defined and managed";
  }

  grouping ncs_compliance_template_aggregation-logical-config {
    description
      "Configuration data for aggregate interfaces";
    leaf lag-type {
      type ncs_compliance_template_aggregation-type;
      description
        "Sets the type of LAG, i.e., how it is
         configured / maintained";
    }
    leaf min-links {
      type string;
      description
        "Specifies the mininum number of member
         interfaces that must be active for the aggregate interface
         to be available";
    }
  }

  grouping ncs_compliance_template_aggregation-logical-state {
    description
      "Operational state data for aggregate interfaces";
    leaf lag-speed {
      type string;
      units "Mbps";
      description
        "Reports effective speed of the aggregate interface,
         based on speed of active member interfaces";
    }
    leaf-list member {
      // NCS patched for predictable order
      ordered-by user;
      // NCS drop when statement
      type oc-if:ncs_compliance_template_base-interface-ref;
      description
        "List of current member interfaces for the aggregate,
         expressed as references to existing interfaces";
    }
  }

  grouping ncs_compliance_template_aggregation-logical-top {
    description
      "Top-level data definitions for LAGs";
    container aggregation {
      description
        "Options for logical interfaces representing
         aggregates";
      container config {
        description
          "Configuration variables for logical aggregate /
           LAG interfaces";
        uses ncs_compliance_template_aggregation-logical-config;
      }
      // NCS drop config false container state
    }
  }

  grouping ncs_compliance_template_ethernet-if-aggregation-config {
    description
      "Adds configuration items for Ethernet interfaces
       belonging to a logical aggregate / LAG";
    leaf aggregate-id {
      type string;
      description
        "Specify the logical aggregate interface to which
         this interface belongs";
    }
  }

  grouping ncs_template_aggregation-logical-config {
    description
      "Configuration data for aggregate interfaces";
    leaf lag-type {
      type ncs_template_aggregation-type;
      description
        "Sets the type of LAG, i.e., how it is
         configured / maintained";
    }
    leaf min-links {
      type string;
      description
        "Specifies the mininum number of member
         interfaces that must be active for the aggregate interface
         to be available";
    }
  }

  grouping ncs_template_aggregation-logical-state {
    description
      "Operational state data for aggregate interfaces";
    leaf lag-speed {
      type string;
      units "Mbps";
      description
        "Reports effective speed of the aggregate interface,
         based on speed of active member interfaces";
    }
    leaf-list member {
      // NCS patched for predictable order
      ordered-by user;
      // NCS drop when statement
      type oc-if:ncs_template_base-interface-ref;
      description
        "List of current member interfaces for the aggregate,
         expressed as references to existing interfaces";
    }
  }

  grouping ncs_template_aggregation-logical-top {
    description
      "Top-level data definitions for LAGs";
    container aggregation {
      description
        "Options for logical interfaces representing
         aggregates";
      container config {
        description
          "Configuration variables for logical aggregate /
           LAG interfaces";
        uses ncs_template_aggregation-logical-config;
      }
      // NCS drop config false container state
    }
  }

  grouping ncs_template_ethernet-if-aggregation-config {
    description
      "Adds configuration items for Ethernet interfaces
       belonging to a logical aggregate / LAG";
    leaf aggregate-id {
      type string;
      description
        "Specify the logical aggregate interface to which
         this interface belongs";
    }
  }

  grouping ncs_rpc_notif_aggregation-logical-config {
    description
      "Configuration data for aggregate interfaces";
    leaf lag-type {
      type ncs_rpc_notif_aggregation-type;
      description
        "Sets the type of LAG, i.e., how it is
         configured / maintained";
    }
    leaf min-links {
      type uint16;
      description
        "Specifies the mininum number of member
         interfaces that must be active for the aggregate interface
         to be available";
    }
  }

  grouping ncs_rpc_notif_aggregation-logical-state {
    description
      "Operational state data for aggregate interfaces";
    leaf lag-speed {
      type uint32;
      units "Mbps";
      description
        "Reports effective speed of the aggregate interface,
         based on speed of active member interfaces";
    }
    leaf-list member {
      when "../../config/lag-type = 'STATIC'" {
        tailf:xpath-root 3;
        description
          "The simple list of member interfaces is active
           when the aggregate is statically configured";
      }
      type oc-if:ncs_rpc_notif_base-interface-ref;
      description
        "List of current member interfaces for the aggregate,
         expressed as references to existing interfaces";
    }
  }

  grouping ncs_rpc_notif_aggregation-logical-top {
    description
      "Top-level data definitions for LAGs";
    container aggregation {
      description
        "Options for logical interfaces representing
         aggregates";
      container config {
        description
          "Configuration variables for logical aggregate /
           LAG interfaces";
        uses ncs_rpc_notif_aggregation-logical-config;
      }
      container state {
        config false;
        description
          "Operational state variables for logical
           aggregate / LAG interfaces";
        uses ncs_rpc_notif_aggregation-logical-config;
        uses ncs_rpc_notif_aggregation-logical-state;
      }
    }
  }

  grouping ncs_rpc_notif_ethernet-if-aggregation-config {
    description
      "Adds configuration items for Ethernet interfaces
       belonging to a logical aggregate / LAG";
    leaf aggregate-id {
      type string;
      description
        "Specify the logical aggregate interface to which
         this interface belongs";
    }
  }

  grouping live_ncs_aggregation-logical-config {
    description
      "Configuration data for aggregate interfaces";
    leaf lag-type {
      type live_ncs_aggregation-type;
      description
        "Sets the type of LAG, i.e., how it is
         configured / maintained";
    }
    leaf min-links {
      type uint16;
      description
        "Specifies the mininum number of member
         interfaces that must be active for the aggregate interface
         to be available";
    }
  }

  grouping live_ncs_aggregation-logical-state {
    description
      "Operational state data for aggregate interfaces";
    leaf lag-speed {
      type uint32;
      units "Mbps";
      description
        "Reports effective speed of the aggregate interface,
         based on speed of active member interfaces";
    }
    leaf-list member {
      // NCS drop when statement
      type oc-if:live_ncs_base-interface-ref;
      description
        "List of current member interfaces for the aggregate,
         expressed as references to existing interfaces";
    }
  }

  grouping live_ncs_aggregation-logical-top {
    description
      "Top-level data definitions for LAGs";
    container aggregation {
      description
        "Options for logical interfaces representing
         aggregates";
      container config {
        description
          "Configuration variables for logical aggregate /
           LAG interfaces";
        uses live_ncs_aggregation-logical-config;
      }
      container state {
        description
          "Operational state variables for logical
           aggregate / LAG interfaces";
        uses live_ncs_aggregation-logical-config;
        uses live_ncs_aggregation-logical-state;
      }
    }
  }

  grouping live_ncs_ethernet-if-aggregation-config {
    description
      "Adds configuration items for Ethernet interfaces
       belonging to a logical aggregate / LAG";
    leaf aggregate-id {
      type leafref {
        path "/ncs:devices/ncs:device/ncs:live-status/oc-if:interfaces/oc-if:interface/oc-if:name" {
          tailf:xpath-root 3;
        }
      }
      description
        "Specify the logical aggregate interface to which
         this interface belongs";
    }
  }

  grouping aggregation-logical-config {
    description
      "Configuration data for aggregate interfaces";
    leaf lag-type {
      type aggregation-type;
      description
        "Sets the type of LAG, i.e., how it is
         configured / maintained";
    }
    leaf min-links {
      type uint16;
      description
        "Specifies the mininum number of member
         interfaces that must be active for the aggregate interface
         to be available";
    }
  }

  grouping aggregation-logical-state {
    description
      "Operational state data for aggregate interfaces";
    leaf lag-speed {
      type uint32;
      units "Mbps";
      description
        "Reports effective speed of the aggregate interface,
         based on speed of active member interfaces";
    }
    leaf-list member {
      when "../../config/lag-type = 'STATIC'" {
        tailf:xpath-root 3;
        description
          "The simple list of member interfaces is active
           when the aggregate is statically configured";
      }
      type oc-if:base-interface-ref;
      description
        "List of current member interfaces for the aggregate,
         expressed as references to existing interfaces";
    }
  }

  grouping aggregation-logical-top {
    description
      "Top-level data definitions for LAGs";
    container aggregation {
      description
        "Options for logical interfaces representing
         aggregates";
      container config {
        description
          "Configuration variables for logical aggregate /
           LAG interfaces";
        uses aggregation-logical-config;
      }
      // NCS drop config false container state
    }
  }

  grouping ethernet-if-aggregation-config {
    description
      "Adds configuration items for Ethernet interfaces
       belonging to a logical aggregate / LAG";
    leaf aggregate-id {
      type leafref {
        path "/ncs:devices/ncs:device/ncs:config/oc-if:interfaces/oc-if:interface/oc-if:name" {
          tailf:xpath-root 3;
        }
      }
      description
        "Specify the logical aggregate interface to which
         this interface belongs";
    }
  }

  augment "/ncs:compliance/ncs:template/ncs:ned-id/ncs:config/oc-if:interfaces/oc-if:interface" {
    description
      "Adds LAG configuration to the interface module";
    uses ncs_compliance_template_aggregation-logical-top {
      // NCS drop when statement
    }
  }
  augment "/ncs:devices/ncs:template/ncs:ned-id/ncs:config/oc-if:interfaces/oc-if:interface" {
    description
      "Adds LAG configuration to the interface module";
    uses ncs_template_aggregation-logical-top {
      // NCS drop when statement
    }
  }
  augment "/ncs:devices/ncs:device/ncs:live-status/oc-if:interfaces/oc-if:interface" {
    description
      "Adds LAG configuration to the interface module";
    uses live_ncs_aggregation-logical-top {
      refine aggregation {
        tailf:ncs-device-type "netconf";
        tailf:display-when "not(../../../../ncs:module) or ../../../../ncs:module[ncs:name='openconfig-if-aggregate'] or (../../../../ncs:live-status-protocol[not(ncs:capability)]) or (../../../../ncs:live-status-protocol/ncs:capability/ncs:module[.='openconfig-if-aggregate'])";
      }
      // NCS drop when statement
    }
  }
  augment "/ncs:devices/ncs:device/ncs:config/oc-if:interfaces/oc-if:interface" {
    description
      "Adds LAG configuration to the interface module";
    uses aggregation-logical-top {
      refine aggregation {
        tailf:ncs-device-type "netconf";
        tailf:display-when "not(../../../../ncs:module) or ../../../../ncs:module[ncs:name='openconfig-if-aggregate']";
      }
      when "oc-if:config/oc-if:type = 'ianaift:ieee8023adLag'" {
        tailf:xpath-root 3;
        description
          "active when the interface is set to type LAG";
      }
    }
  }
  augment "/ncs:compliance/ncs:template/ncs:ned-id/ncs:config/oc-if:interfaces/oc-if:interface/oc-eth:ethernet/oc-eth:config" {
    description
      "Adds LAG settings to individual Ethernet interfaces";
    uses ncs_compliance_template_ethernet-if-aggregation-config;
  }
  augment "/ncs:devices/ncs:template/ncs:ned-id/ncs:config/oc-if:interfaces/oc-if:interface/oc-eth:ethernet/oc-eth:config" {
    description
      "Adds LAG settings to individual Ethernet interfaces";
    uses ncs_template_ethernet-if-aggregation-config;
  }
  augment "/ncs:devices/ncs:device/ncs:live-status/oc-if:interfaces/oc-if:interface/oc-eth:ethernet/oc-eth:config" {
    description
      "Adds LAG settings to individual Ethernet interfaces";
    uses live_ncs_ethernet-if-aggregation-config {
      refine aggregate-id {
        tailf:ncs-device-type "netconf";
        tailf:display-when "not(../../../../../../ncs:module) or ../../../../../../ncs:module[ncs:name='openconfig-if-aggregate'] or (../../../../../../ncs:live-status-protocol[not(ncs:capability)]) or (../../../../../../ncs:live-status-protocol/ncs:capability/ncs:module[.='openconfig-if-aggregate'])";
      }
    }
  }
  augment "/ncs:devices/ncs:device/ncs:config/oc-if:interfaces/oc-if:interface/oc-eth:ethernet/oc-eth:config" {
    description
      "Adds LAG settings to individual Ethernet interfaces";
    uses ethernet-if-aggregation-config {
      refine aggregate-id {
        tailf:ncs-device-type "netconf";
        tailf:display-when "not(../../../../../../ncs:module) or ../../../../../../ncs:module[ncs:name='openconfig-if-aggregate']";
      }
    }
  }
  augment "/ncs:devices/ncs:device/ncs:live-status/oc-if:interfaces/oc-if:interface/oc-eth:ethernet/oc-eth:state" {
    description
      "Adds LAG settings to individual Ethernet interfaces";
    uses live_ncs_ethernet-if-aggregation-config {
      refine aggregate-id {
        tailf:ncs-device-type "netconf";
        tailf:display-when "not(../../../../../../ncs:module) or ../../../../../../ncs:module[ncs:name='openconfig-if-aggregate'] or (../../../../../../ncs:live-status-protocol[not(ncs:capability)]) or (../../../../../../ncs:live-status-protocol/ncs:capability/ncs:module[.='openconfig-if-aggregate'])";
      }
    }
  }
}
